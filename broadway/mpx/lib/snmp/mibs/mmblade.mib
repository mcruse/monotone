-- ********************************************************************************
-- ********************************************************************************
--
-- File         : mmblade.mib
-- Description  : IBM Management Module MIB for SNMP
-- Version      : 4.5
-- Date         : October 2008
-- Copyright (c) 2002-2008 IBM  All Rights Reserved.
-- ********************************************************************************
--
-- Contains MIB description for:
--   This MIB is to be used to provide configuration support and monitoring for the 
--   BladeCenter, BladeCenter T, BladeCenter H, and BladeCenter HT.
--
-- ********************************************************************************
-- ********************************************************************************
-- ********************************************************************************
        BLADE-MIB DEFINITIONS ::= BEGIN


        IMPORTS
            -- OBJECT-TYPE                          FROM RFC-1212
            -- enterprises                          FROM RFC1155-SMI
            -- DisplayString                        FROM RFC1213-MIB
            -- IpAddress                            FROM RFC1155-SMI
            OBJECT-TYPE                          FROM SNMPv2-SMI
            enterprises                          FROM SNMPv2-SMI
            MODULE-IDENTITY                      FROM SNMPv2-SMI
            DisplayString                        FROM SNMPv2-TC
            TEXTUAL-CONVENTION                   FROM SNMPv2-TC
            IpAddress                            FROM SNMPv2-SMI
            Integer32                            FROM SNMPv2-SMI
            ;
            -- TRAP-TYPE                            FROM RFC-1215;

        -- IBM BladeCenter Management Module (MM)
        -- Also known as Advanced System Mangement (ASM) or Support Processor (SP)
        bladeCenterSnmpMIB     MODULE-IDENTITY
                LAST-UPDATED "200907310145Z"  -- Made up from October 2008 above.
                ORGANIZATION "Cisco Systems, Inc."
                CONTACT-INFO
                        "       Cisco Systems, Inc. 
                                170 West Tasman Dr.
                                San Jose, CA 95134
                                USA
                                (408)526-4000
                                (800)553-NETS or (800)553-6387"
                DESCRIPTION
                  "  Cisco NBM port of the IBM BladeCenter Management Module
                     (MM).  Also known as Advanced System Mangement (ASM) or
                     Support Processor (SP)"
                REVISION     "200907310145Z"  -- July 31, 2009
                DESCRIPTION  "Ported for compilation via smidump:
                              1. Replaced import of RFC-1212, FROM RFC1155-SMI,
                                 RFC1213-MIB and RFC1155-SMI with SNMPv2-SMI
                                 and SNMPv2-TC.
                              2. Removed unused import of TRAP-TYPE.
                              3. Added imports of:  MODULE-IDENTITY,
                                 DisplayString, TEXTUAL-CONVENTION and
                                 Integer32.
                              4. Change all ACCESS statements to MAX-ACCESS,
                              5. Change all OIDs used as indexes from INTEGER
                                 to Integer32 (0..2147483647).
                              6. Converted bladeCenterSnmpMIB into the module's
                                 MODULE-IDENTITY.
                              "
                REVISION     "200810310001Z"  -- Made up from October 2008 above.
                DESCRIPTION  "Last IBM update"
                 ::= { netfinitySupportProcessorAgent 2 }

            -- textual conventions
            EntryStatus ::= INTEGER
                         { valid(1),
                           createRequest(2),
                           underCreation(3),
                           invalid(4)
                         }
            InetAddressIPv6 ::= TEXTUAL-CONVENTION
                        DISPLAY-HINT "2x:2x:2x:2x:2x:2x:2x:2x"
                        STATUS       current
                        DESCRIPTION
                                "Represents an IPv6 network address:

                                Octets   Contents         Encoding
                        1-16    IPv6 address     network-byte order

                                The corresponding InetAddressType value is ipv6(2).

                                This textual convention SHOULD NOT be used directly in object
                                definitions, as it restricts addresses to a specific format.
                                However, if it is used, it MAY be used either on its own or in
                                conjunction with InetAddressType, as a pair."
                        SYNTAX       OCTET STRING (SIZE (16))

              -- The status of a table entry.
              --
              -- Setting this object to the value invalid(4) has the
              -- effect of invalidating the corresponding entry.
              -- That is, it effectively disassociates the mapping
              -- identified with said entry.
              -- It is an implementation-specific matter as to whether
              -- the agent removes an invalidated entry from the table.
              -- Accordingly, management stations must be prepared to
              -- receive tabular information from agents that corresponds
              -- to entries currently not in use.  Proper
              -- interpretation of such entries requires examination
              -- of the relevant EntryStatus object.
              --
              -- An existing instance of this object cannot be set to
              -- createRequest(2).  This object may only be set to
              -- createRequest(2) when this instance is created.  When
              -- this object is created, the agent may wish to create
              -- supplemental object instances to complete a conceptual
              -- row in this table.  Immediately after completing the
              -- create operation, the agent must set this object to
              -- underCreation(3).
              --
              -- Entries shall exist in the underCreation(3) state until

              -- the management station is finished configuring the
              -- entry and sets this object to valid(1) or aborts,
              -- setting this object to invalid(4).  If the agent
              -- determines that an entry has been in the
              -- underCreation(3) state for an abnormally long time,
              -- it may decide that the management station has
              -- crashed.  If the agent makes this decision,
              -- it may set this object to invalid(4) to reclaim the
              -- entry.  A prudent agent will understand that the
              -- management station may need to wait for human input
              -- and will allow for that possibility in its
              -- determination of this abnormally long period.

        -- IBM enterprise group
        ibm         OBJECT IDENTIFIER ::=   { enterprises 2 }

        -- IBM products group
        ibmAgents      OBJECT IDENTIFIER ::=   { ibm 3 }

        -- IBM Advanced System Management Support Processor (SP) agent group
        netfinitySupportProcessorAgent OBJECT IDENTIFIER ::= { ibmAgents 51 }

-- ********************************************************************************
-- Start: Define groups of objects within the bladeCenterSnmpMIB
-- ********************************************************************************
  -- This group of objects provides the various environmental monitors for the
  -- local system and the MM
  monitors OBJECT IDENTIFIER ::= { bladeCenterSnmpMIB 2 }

  -- This group of objects provides the error log objects for the MM
  errorLogs OBJECT IDENTIFIER ::= { bladeCenterSnmpMIB 3 }

  -- This group of objects provides configuration functions for the MM
  configureSP     OBJECT IDENTIFIER ::= { bladeCenterSnmpMIB 4 }

  -- This group of objects provides system management functions for BladeCenter T
  telcoManagement  OBJECT IDENTIFIER ::= { bladeCenterSnmpMIB 5 }

  -- This group of objects provides configuration functions for system power
--  systemPower  OBJECT IDENTIFIER ::= { bladeCenterSnmpMIB 6 }

  -- This group of objects provides functions to boot the MM and system
  restartReset      OBJECT IDENTIFIER ::= { bladeCenterSnmpMIB 7 }

  -- This group of objects provides information specific to blades
  blades OBJECT IDENTIFIER ::= { bladeCenterSnmpMIB 22 }

  -- This group of objects provides information on the PCI-X expansion enclosure
  -- pcixExpansionBox      OBJECT IDENTIFIER ::= { bladeCenterSnmpMIB 21 }

  -- This group of objects provides information specific to service
  service OBJECT IDENTIFIER ::= { bladeCenterSnmpMIB 23 }

    -- ********************************************************************************
    -- Temperature
    -- ********************************************************************************
    temperature OBJECT IDENTIFIER ::= { monitors 1 }

     -- Planar Temperature
     planarTemp OBJECT IDENTIFIER ::= { temperature 1 }

      mmTemp      OBJECT-TYPE
                   SYNTAX  OCTET STRING
                   MAX-ACCESS  read-only
                   STATUS  current -- was mandatory
                   DESCRIPTION
                   "Management module temperature in degrees centigrade(C).
                   An octet string expressed as 'sddd.dd Centigrade' where:
                   s is the sign ('-' for negative or blank space for positive)
                   d is a decimal digit or blank space for leading zeroes.
                   The string 'Not Readable!' indicates that the given monitor
                   is not supported on this system."
                   ::= { planarTemp 2 }


     -- CPUx Temperature
     -- cpuXTemp OBJECT IDENTIFIER ::= { temperature 2 }

     -- System Ambient Temperature
     ambientTemp OBJECT IDENTIFIER ::= { temperature 5 }

      frontPanelTemp    OBJECT-TYPE
                   SYNTAX  OCTET STRING
                   MAX-ACCESS  read-only
                   STATUS  current -- was mandatory
                   DESCRIPTION
                   "The front panel temperature in degrees centigrade(C).
                   This is surrounding temperature where the system is installed.
                   An octet string expressed as 'sddd.dd Centigrade' where:
                   s is the sign ('-' for negative or blank space for positive)
                   d is a decimal digit or blank space for a leading zero.
                   The string 'Not Readable!' indicates that the given monitor
                   is not supported on this system."
                   ::= { ambientTemp 1 }
                   
      frontPanel2Temp    OBJECT-TYPE
                   SYNTAX  OCTET STRING
                   MAX-ACCESS  read-only
                   STATUS  current -- was mandatory
                   DESCRIPTION
                   "The front panel 2 temperature in degrees centigrade(C).
                   This is surrounding temperature where the system is installed.
                   An octet string expressed as 'sddd.dd Centigrade' where:
                   s is the sign ('-' for negative or blank space for positive)
                   d is a decimal digit or blank space for a leading zero.
                   The string 'Not Readable!' indicates that the given monitor
                   is not supported on this system.
                   NOTE: This MIB object is for BladeCenter HT only"
                   ::= { ambientTemp 2 }


    -- ********************************************************************************
    -- Voltages
    -- ********************************************************************************
    voltage OBJECT IDENTIFIER ::= { monitors 2 }

     -- Planar Voltages
     planarVolt OBJECT IDENTIFIER ::= { voltage 1 }

      plus5Volt    OBJECT-TYPE
                   SYNTAX  OCTET STRING
                   MAX-ACCESS  read-only
                   STATUS  current -- was mandatory
                   DESCRIPTION
                   "+5 Volt power supply voltage reading expressed in Volts(V).
                   An octet string expressed as 'sdd.dd Volts' where:
                   s is the sign ('-' for negative or '+' for positive)
                   d is a decimal digit or blank space for a leading zero.
                   The string 'Not Readable!' indicates that the given monitor
                   is not supported on this system."
                   ::= { planarVolt 1 }

      plus3Pt3Volt OBJECT-TYPE
                   SYNTAX  OCTET STRING
                   MAX-ACCESS  read-only
                   STATUS  current -- was mandatory
                   DESCRIPTION
                   "+3.3 Volt power supply voltage reading expressed in Volts(V).
                   An octet string expressed as 'sdd.dd Volts' where:
                   s is the sign ('-' for negative or '+' for positive)
                   d is a decimal digit or blank space for a leading zero.
                   The string 'Not Readable!' indicates that the given monitor
                   is not supported on this system."
                   ::= { planarVolt 2 }

      plus12Volt   OBJECT-TYPE
                   SYNTAX  OCTET STRING
                   MAX-ACCESS  read-only
                   STATUS  current -- was mandatory
                   DESCRIPTION
                   "+12 Volt power supply voltage reading expressed in Volts(V).
                   An octet string expressed as 'sdd.dd Volts' where:
                   s is the sign ('-' for negative or '+' for positive)
                   d is a decimal digit or blank space for a leading zero.
                   The string 'Not Readable!' indicates that the given monitor
                   is not supported on this system."
                   ::= { planarVolt 3 }

      minus5Volt   OBJECT-TYPE
                   SYNTAX  OCTET STRING
                   MAX-ACCESS  read-only
                   STATUS  current -- was mandatory
                   DESCRIPTION
                   "-5 Volt power supply voltage reading expressed in Volts(V).
                   An octet string expressed as 'sdd.dd Volts' where:
                   s is the sign ('-' for negative or '+' for positive)
                   d is a decimal digit or blank space for a leading zero.
                   The string 'Not Readable!' indicates that the given monitor
                   is not supported on this system."
                   ::= { planarVolt 5 }

      plus2Pt5Volt OBJECT-TYPE
                   SYNTAX  OCTET STRING
                   MAX-ACCESS  read-only
                   STATUS  current -- was mandatory
                   DESCRIPTION
                   "+2.5 Volt power supply voltage reading expressed in Volts(V).
                   An octet string expressed as 'sdd.dd Volts' where:
                   s is the sign ('-' for negative or '+' for positive)
                   d is a decimal digit or blank space for a leading zero.
                   The string 'Not Readable!' indicates that the given monitor
                   is not supported on this system."
                   ::= { planarVolt 6 }

      plus1Pt8Volt OBJECT-TYPE
                   SYNTAX  OCTET STRING
                   MAX-ACCESS  read-only
                   STATUS  current -- was mandatory
                   DESCRIPTION
                   "+1.8 Volt power supply voltage reading expressed in Volts(V).
                   An octet string expressed as 'sdd.dd Volts' where:
                   s is the sign ('-' for negative or '+' for positive)
                   d is a decimal digit or blank space for a leading zero.
                   The string 'Not Readable!' indicates that the given monitor
                   is not supported on this system."
                   ::= { planarVolt 8 }

    -- ********************************************************************************
    -- Blowers
    -- ********************************************************************************
    blowers OBJECT IDENTIFIER ::= { monitors 3 }

     blower1speed OBJECT-TYPE
                  SYNTAX  OCTET STRING
                  MAX-ACCESS  read-only
                  STATUS  current -- was mandatory
                  DESCRIPTION
                  "Blower 1 speed expressed in percent(%) of maximum RPM.
                  An octet string expressed as 'ddd% of maximum' where:
                  d is a decimal digit or blank space for a leading zero.
                  If the blower is determined not to be running or
                  the blower speed cannot be determined, the string will
                  indicate 'Offline'.
                  The string 'Not Readable!' indicates that the given monitor
                  is not supported on this system.

                  NOTE: Blowers are also referred to as Chassis Cooling Devices."
                  ::= { blowers 1 }

     blower2speed OBJECT-TYPE
                  SYNTAX  OCTET STRING
                  MAX-ACCESS  read-only
                  STATUS  current -- was mandatory
                  DESCRIPTION
                  "Blower 2 speed expressed in percent(%) of maximum RPM.
                  An octet string expressed as 'ddd% of maximum' where:
                  d is a decimal digit or blank space for a leading zero.
                  If the blower is determined not to be running or
                  the blower speed cannot be determined, the string will
                  indicate 'Offline'.
                  The string 'Not Readable!' indicates that the given monitor
                  is not supported on this system.

                  NOTE: Blowers are also referred to as Chassis Cooling Devices."
                  ::= { blowers 2 }

     blower3speed OBJECT-TYPE
                  SYNTAX  OCTET STRING
                  MAX-ACCESS  read-only
                  STATUS  current -- was mandatory
                  DESCRIPTION
                  "Blower 3 speed expressed in percent(%) of maximum RPM.
                  An octet string expressed as 'ddd% of maximum' where:
                  d is a decimal digit or blank space for a leading zero.
                  If the blower is determined not to be running or
                  the blower speed cannot be determined, the string will
                  indicate 'Offline'.
                  The string 'Not Readable!' indicates that the given monitor
                  is not supported on this system.

                  NOTE: This MIB object is for BladeCenter T only.
                  NOTE: Blowers are also referred to as Chassis Cooling Devices."
                  ::= { blowers 3 }

     blower4speed OBJECT-TYPE
                  SYNTAX  OCTET STRING
                  MAX-ACCESS  read-only
                  STATUS  current -- was mandatory
                  DESCRIPTION
                  "Blower 4 speed expressed in percent(%) of maximum RPM.
                  An octet string expressed as 'ddd% of maximum' where:
                  d is a decimal digit or blank space for a leading zero.
                  If the blower is determined not to be running or
                  the blower speed cannot be determined, the string will
                  indicate 'Offline'.
                  The string 'Not Readable!' indicates that the given monitor
                  is not supported on this system.

                  NOTE: This MIB object is for BladeCenter T only.
                  NOTE: Blowers are also referred to as Chassis Cooling Devices."
                  ::= { blowers 4 }

     blower1State  OBJECT-TYPE
                   SYNTAX  INTEGER {
                     unknown(0),
                     good(1),
                     warning(2),
                     bad(3)
                   }
                   MAX-ACCESS  read-only
                   STATUS  current -- was mandatory
                   DESCRIPTION
                   "The health state for blower 1.

                   NOTE: Blowers are also referred to as Chassis Cooling Devices."
                   ::= { blowers 10}
                   
     blower2State  OBJECT-TYPE
                   SYNTAX  INTEGER {
                     unknown(0),
                     good(1),
                     warning(2),
                     bad(3)
                   }
                   MAX-ACCESS  read-only
                   STATUS  current -- was mandatory
                   DESCRIPTION
                   "The health state for blower 2.

                   NOTE: Blowers are also referred to as Chassis Cooling Devices."
                   ::= { blowers 11}

     blower3State  OBJECT-TYPE
                   SYNTAX  INTEGER {
                     unknown(0),
                     good(1),
                     warning(2),
                     bad(3)
                   }
                   MAX-ACCESS  read-only
                   STATUS  current -- was mandatory
                   DESCRIPTION
                   "The health state for blower 3.

                   NOTE: This MIB object is for BladeCenter T only.
                   NOTE: Blowers are also referred to as Chassis Cooling Devices."
                   ::= { blowers 12}

     blower4State  OBJECT-TYPE
                   SYNTAX  INTEGER {
                     unknown(0),
                     good(1),
                     warning(2),
                     bad(3)
                   }
                   MAX-ACCESS  read-only
                   STATUS  current -- was mandatory
                   DESCRIPTION
                   "The health state for blower 4.

                   NOTE: This MIB object is for BladeCenter T only.
                   NOTE: Blowers are also referred to as Chassis Cooling Devices."
                   ::= { blowers 13}

     blower1speedRPM    OBJECT-TYPE
                  SYNTAX  OCTET STRING
                  MAX-ACCESS  read-only
                  STATUS  current -- was mandatory
                  DESCRIPTION
                  "Blower 1 speed expressed in RPM.
                  If the blower is determined not to be running or
                  the blower speed cannot be determined, the string will
                  indicate 'Offline'.
                  The string 'Not Readable!' indicates that the given monitor
                  is not supported on this system.

                  NOTE: This MIB object is for AMM installed in BladeCenter H only.
                  NOTE: Blowers are also referred to as Chassis Cooling Devices."
                  ::= { blowers 20 }

     blower2speedRPM    OBJECT-TYPE
                  SYNTAX  OCTET STRING
                  MAX-ACCESS  read-only
                  STATUS  current -- was mandatory
                  DESCRIPTION
                  "Blower 2 speed expressed in RPM.
                  If the blower is determined not to be running or
                  the blower speed cannot be determined, the string will
                  indicate 'Offline'.
                  The string 'Not Readable!' indicates that the given monitor
                  is not supported on this system.

                  NOTE: This MIB object is for AMM installed in BladeCenter H only.
                  NOTE: Blowers are also referred to as Chassis Cooling Devices."
                  ::= { blowers 21 }
                  
     blower3speedRPM    OBJECT-TYPE
                  SYNTAX  OCTET STRING
                  MAX-ACCESS  read-only
                  STATUS  current -- was mandatory
                  DESCRIPTION
                  "Blower 3 speed expressed in RPM.
                  If the blower is determined not to be running or
                  the blower speed cannot be determined, the string will
                  indicate 'Offline'.
                  The string 'Not Readable!' indicates that the given monitor
                  is not supported on this system.

                  NOTE: This MIB object is for AMM installed in BladeCenter HT only.
                  NOTE: Blowers are also referred to as Chassis Cooling Devices."
                  ::= { blowers 22 }

     blower4speedRPM    OBJECT-TYPE
                  SYNTAX  OCTET STRING
                  MAX-ACCESS  read-only
                  STATUS  current -- was mandatory
                  DESCRIPTION
                  "Blower 4 speed expressed in RPM.
                  If the blower is determined not to be running or
                  the blower speed cannot be determined, the string will
                  indicate 'Offline'.
                  The string 'Not Readable!' indicates that the given monitor
                  is not supported on this system.

                  NOTE: This MIB object is for AMM installed in BladeCenter HT only.
                  NOTE: Blowers are also referred to as Chassis Cooling Devices."
                  ::= { blowers 23 }

     blower1ControllerState    OBJECT-TYPE
                   SYNTAX  INTEGER {
                     operational(0),
                     flashing(1),
                     notPresent(2),
                     communicationError(3),
                     unknown(255)
                   }
                   MAX-ACCESS  read-only
                   STATUS  current -- was mandatory
                   DESCRIPTION
                   "The health state for the controller for blower 1.

                   NOTE: This MIB object is for AMM installed in BladeCenter H only.
                   NOTE: Blowers are also referred to as Chassis Cooling Devices."
                   ::= { blowers 30}

     blower2ControllerState    OBJECT-TYPE
                   SYNTAX  INTEGER {
                     operational(0),
                     flashing(1),
                     notPresent(2),
                     communicationError(3), 
                     unknown(255)
                   }
                   MAX-ACCESS  read-only
                   STATUS  current -- was mandatory
                   DESCRIPTION
                   "The health state for the controller for blower 2.

                   NOTE: This MIB object is for AMM installed in BladeCenter H only.
                   NOTE: Blowers are also referred to as Chassis Cooling Devices."
                   ::= { blowers 31}

     blower3ControllerState    OBJECT-TYPE
                   SYNTAX  INTEGER {
                     operational(0),
                     flashing(1),
                     notPresent(2),
                     communicationError(3),
                     unknown(255)
                   }
                   MAX-ACCESS  read-only
                   STATUS  current -- was mandatory
                   DESCRIPTION
                   "The health state for the controller for blower 3.

                   NOTE: This MIB object is for AMM installed in BladeCenter HT only.
                   NOTE: Blowers are also referred to as Chassis Cooling Devices."
                   ::= { blowers 32}

     blower4ControllerState    OBJECT-TYPE
                   SYNTAX  INTEGER {
                     operational(0),
                     flashing(1),
                     notPresent(2),
                     communicationError(3), 
                     unknown(255)
                   }
                   MAX-ACCESS  read-only
                   STATUS  current -- was mandatory
                   DESCRIPTION
                   "The health state for the controller for blower 4.

                   NOTE: This MIB object is for AMM installed in BladeCenter HT only.
                   NOTE: Blowers are also referred to as Chassis Cooling Devices."
                   ::= { blowers 33}
    
     blower1ExhaustTemp    OBJECT-TYPE
                   SYNTAX  OCTET STRING
                   MAX-ACCESS  read-only
                   STATUS  current -- was mandatory
                   DESCRIPTION
                   "The exhaust temperature in degrees Celsius for blower 1.

                   NOTE: This MIB object is for BCS only.
                   NOTE: Blowers are also referred to as Chassis Cooling Devices."
                   ::= { blowers 40}
    
     blower2ExhaustTemp    OBJECT-TYPE
                   SYNTAX  OCTET STRING
                   MAX-ACCESS  read-only
                   STATUS  current -- was mandatory
                   DESCRIPTION
                   "The exhaust temperature in degrees Celsius for blower 2.

                   NOTE: This MIB object is for BCS only.
                   NOTE: Blowers are also referred to as Chassis Cooling Devices."
                   ::= { blowers 41}
    
     blower3ExhaustTemp    OBJECT-TYPE
                   SYNTAX  OCTET STRING
                   MAX-ACCESS  read-only
                   STATUS  current -- was mandatory
                   DESCRIPTION
                   "The exhaust temperature in degrees Celsius for blower 3.

                   NOTE: This MIB object is for BCS only.
                   NOTE: Blowers are also referred to as Chassis Cooling Devices."
                   ::= { blowers 42}
    
     blower4ExhaustTemp    OBJECT-TYPE
                   SYNTAX  OCTET STRING
                   MAX-ACCESS  read-only
                   STATUS  current -- was mandatory
                   DESCRIPTION
                   "The exhaust temperature in degrees Celsius for blower 4.

                   NOTE: This MIB object is for BCS only.
                   NOTE: Blowers are also referred to as Chassis Cooling Devices."
                   ::= { blowers 43}
    
    -- ********************************************************************************
    -- Power Module Health State
    -- ********************************************************************************
    powerModuleHealth OBJECT IDENTIFIER ::= { monitors 4 }
    
      powerModuleHealthTable OBJECT-TYPE
                     SYNTAX  SEQUENCE OF PowerModuleHealthEntry
                     MAX-ACCESS  not-accessible
                     STATUS  current -- was mandatory
                     DESCRIPTION
                     "Table of power module health information.  Contains
                     the power health information for each power module."
                     ::= { powerModuleHealth 1 }

       powerModuleHealthEntry OBJECT-TYPE
                     SYNTAX PowerModuleHealthEntry
                     MAX-ACCESS  not-accessible
                     STATUS  current -- was mandatory
                     DESCRIPTION
                     "Power Module health entry"
                     INDEX { powerModuleIndex }
                     ::= { powerModuleHealthTable 1 }


       PowerModuleHealthEntry ::= SEQUENCE {
                   powerModuleIndex INTEGER,
                   powerModuleExists INTEGER,
                   powerModuleState INTEGER,
                   powerModuleDetails OCTET STRING
                   }

       powerModuleIndex  OBJECT-TYPE
                   SYNTAX  Integer32 (0..2147483647) -- was INTEGER
                   MAX-ACCESS  read-only
                   STATUS  current -- was mandatory
                   DESCRIPTION
                   "Power module sequence index."
                   ::= { powerModuleHealthEntry 1 }
                   
       powerModuleExists OBJECT-TYPE
                   SYNTAX  INTEGER {
                     false(0),
                     true(1)
                   }
                   MAX-ACCESS  read-only
                   STATUS  current -- was mandatory
                   DESCRIPTION
                   "Indicates whether the power module specified exists or not."
                   ::= { powerModuleHealthEntry 2 }

       powerModuleState OBJECT-TYPE
                   SYNTAX  INTEGER {
                     unknown(0),
                     good(1),
                     warning(2),
                     notAvailable(3),
                     critical(4)
                   }
                   MAX-ACCESS  read-only
                   STATUS  current -- was mandatory
                   DESCRIPTION
                   "The health state for the power module."
                   ::= { powerModuleHealthEntry 3}

       powerModuleDetails OBJECT-TYPE
                   SYNTAX  OCTET STRING 
                   MAX-ACCESS  read-only
                   STATUS  current -- was mandatory
                   DESCRIPTION
                   "The details for this power module."
                   ::= { powerModuleHealthEntry 4 }

    -- ********************************************************************************
    -- MM Status
    -- ********************************************************************************
    spStatus OBJECT IDENTIFIER ::= { monitors 5 }

     mmBistAndChassisStatus OBJECT IDENTIFIER ::= { spStatus 2 }


      bistSdram  OBJECT-TYPE
                  SYNTAX  INTEGER {
                    testSucceeded(0),
                    testFailed(1)
                  }
                  MAX-ACCESS  read-only
                  STATUS  current -- was mandatory
                  DESCRIPTION
                  "MM BIST DRAM test result."
                  ::= { mmBistAndChassisStatus 1 }

      bistRs485Port1 OBJECT-TYPE
                  SYNTAX  INTEGER {
                    testSucceeded(0),
                    testFailed(1)
                  }
                  MAX-ACCESS  read-only
                  STATUS  current -- was mandatory
                  DESCRIPTION
                  "MM BIST RS 485 legacy test result."
                  ::= { mmBistAndChassisStatus 2 }

      bistRs485Port2 OBJECT-TYPE
                  SYNTAX  INTEGER {
                    testSucceeded(0),
                    testFailed(1)
                  }
                  MAX-ACCESS  read-only
                  STATUS  current -- was mandatory
                  DESCRIPTION
                  "MM BIST RS 485 local bus test result."
                  ::= { mmBistAndChassisStatus 3 }

      bistNvram  OBJECT-TYPE
                  SYNTAX  INTEGER {
                    testSucceeded(0),
                    testFailed(1)
                  }
                  MAX-ACCESS  read-only
                  STATUS  current -- was mandatory
                  DESCRIPTION
                  "MM BIST NVRAM test result."
                  ::= { mmBistAndChassisStatus 4 }

      bistRtc OBJECT-TYPE
                  SYNTAX  INTEGER {
                    testSucceeded(0),
                    testFailed(1)
                  }
                  MAX-ACCESS  read-only
                  STATUS  current -- was mandatory
                  DESCRIPTION
                  "MM BIST Real Time Clock test result."
                  ::= { mmBistAndChassisStatus 5 }

      bistLocalI2CBus OBJECT-TYPE
                  SYNTAX  INTEGER {
                    testSucceeded(0),
                    testFailed(1)
                  }
                  MAX-ACCESS  read-only
                  STATUS  current -- was mandatory
                  DESCRIPTION
                  "MM BIST Local I2C bus test result."
                  ::= { mmBistAndChassisStatus 7 }

      bistPrimaryMainAppFlashImage  OBJECT-TYPE
                  SYNTAX  INTEGER {
                    testSucceeded(0),
                    testFailed(1)
                  }
                  MAX-ACCESS  read-only
                  STATUS  current -- was mandatory
                  DESCRIPTION
                  "MM BIST Primary Main Application Firmware test result."
                  ::= { mmBistAndChassisStatus 8 }

      bistSecondaryMainAppFlashImage  OBJECT-TYPE
                  SYNTAX  INTEGER {
                    testSucceeded(0),
                    testFailed(1)
                  }
                  MAX-ACCESS  read-only
                  STATUS  current -- was mandatory
                  DESCRIPTION
                  "MM BIST Secondary Main Application test result."
                  ::= { mmBistAndChassisStatus 9 }

      bistBootRomFlashImage  OBJECT-TYPE
                  SYNTAX  INTEGER {
                    testSucceeded(0),
                    testFailed(1)
                  }
                  MAX-ACCESS  read-only
                  STATUS  current -- was mandatory
                  DESCRIPTION
                  "MM BIST Boot Firmware test result."
                  ::= { mmBistAndChassisStatus 10 }

      bistEthernetPort1 OBJECT-TYPE
                  SYNTAX  INTEGER {
                    testSucceeded(0),
                    testFailed(1)
                  }
                  MAX-ACCESS  read-only
                  STATUS  current -- was mandatory
                  DESCRIPTION
                  "MM BIST external ethernet port test result."
                  ::= { mmBistAndChassisStatus 11 }

      bistEthernetPort2 OBJECT-TYPE
                  SYNTAX  INTEGER {
                    testSucceeded(0),
                    testFailed(1)
                  }
                  MAX-ACCESS  read-only
                  STATUS  current -- was mandatory
                  DESCRIPTION
                  "MM BIST internal ethernet port test result."
                  ::= { mmBistAndChassisStatus 12 }

      bistInternalPCIBus OBJECT-TYPE
                  SYNTAX  INTEGER {
                    testSucceeded(0),
                    testFailed(1)
                  }
                  MAX-ACCESS  read-only
                  STATUS  current -- was mandatory
                  DESCRIPTION
                  "MM BIST PCI bus test result."
                  ::= { mmBistAndChassisStatus 13 }

      bistExternalI2CDevices OBJECT-TYPE
                  SYNTAX  INTEGER {
                    testSucceeded(0),
                    testFailed(1)
                  }
                  MAX-ACCESS  read-only
                  STATUS  current -- was mandatory
                  DESCRIPTION
                  "MM BIST external I2C devices test result."
                  ::= { mmBistAndChassisStatus 14 }

      bistUSBController OBJECT-TYPE
                  SYNTAX  INTEGER {
                    testSucceeded(0),
                    testFailed(1)
                  }
                  MAX-ACCESS  read-only
                  STATUS  current -- was mandatory
                  DESCRIPTION
                  "MM BIST USB controller test result."
                  ::= { mmBistAndChassisStatus 15 }

      bistVideoCompressorBoard OBJECT-TYPE
                  SYNTAX  INTEGER {
                    testSucceeded(0),
                    testFailed(1)
                  }
                  MAX-ACCESS  read-only
                  STATUS  current -- was mandatory
                  DESCRIPTION
                  "MM BIST Video Compressor Board test result."
                  ::= { mmBistAndChassisStatus 16 }
      
      bistRemoteVideo OBJECT-TYPE
                  SYNTAX  INTEGER {
                    testSucceeded(0),
                    testFailed(1)
                  }
                  MAX-ACCESS  read-only
                  STATUS  current -- was mandatory
                  DESCRIPTION
                  "MM BIST Remote Video test result."
                  ::= { mmBistAndChassisStatus 17 }

      bistPrimaryBus OBJECT-TYPE
                  SYNTAX  INTEGER {
                    testSucceeded(0),
                    testFailed(1)
                  }
                  MAX-ACCESS  read-only
                  STATUS  current -- was mandatory
                  DESCRIPTION
                  "MM BIST primary mid-plane bus test result."
                  ::= { mmBistAndChassisStatus 18 }

      bistInternalEthernetSwitch OBJECT-TYPE
                  SYNTAX  INTEGER {
                    testSucceeded(0),
                    testFailed(1)
                  }
                  MAX-ACCESS  read-only
                  STATUS  current -- was mandatory
                  DESCRIPTION
                  "MM BIST internal external switch test result."
                  ::= { mmBistAndChassisStatus 19 }

      bistVideoCapture OBJECT-TYPE
                  SYNTAX  INTEGER {
                    testSucceeded(0),
                    testFailed(1)
                  }
                  MAX-ACCESS  read-only
                  STATUS  current -- was mandatory
                  DESCRIPTION
                  "MM BIST video capture test result."
                  ::= { mmBistAndChassisStatus 20 }

      bistUSBKeyboardMouseEmulation OBJECT-TYPE
                  SYNTAX  INTEGER {
                    testSucceeded(0),
                    testFailed(1)
                  }
                  MAX-ACCESS  read-only
                  STATUS  current -- was mandatory
                  DESCRIPTION
                  "MM BIST USB keyboard and mouse test result."
                  ::= { mmBistAndChassisStatus 21 }
                  
      bistUSBMassStorageEmulation OBJECT-TYPE
                  SYNTAX  INTEGER {
                    testSucceeded(0),
                    testFailed(1)
                  }
                  MAX-ACCESS  read-only
                  STATUS  current -- was mandatory
                  DESCRIPTION
                  "MM BIST mass storage emulation test result."
                  ::= { mmBistAndChassisStatus 22 }
      
      bistUSBKeyboardMouseFirmware OBJECT-TYPE
                  SYNTAX  INTEGER {
                    testSucceeded(0),
                    testFailed(1)
                  }
                  MAX-ACCESS  read-only
                  STATUS  current -- was mandatory
                  DESCRIPTION
                  "MM BIST USB keyboard and mouse firmware test result."
                  ::= { mmBistAndChassisStatus 23 }

      bistUSBMassStorageFirmware OBJECT-TYPE
                  SYNTAX  INTEGER {
                    testSucceeded(0),
                    testFailed(1)
                  }
                  MAX-ACCESS  read-only
                  STATUS  current -- was mandatory
                  DESCRIPTION
                  "MM BIST USB keyboard mouse firmware test result."
                  ::= { mmBistAndChassisStatus 24 }

      bistPrimaryCore OBJECT-TYPE
                  SYNTAX  INTEGER {
                    testSucceeded(0),
                    testFailed(1)
                  }
                  MAX-ACCESS  read-only
                  STATUS  current -- was mandatory
                  DESCRIPTION
                  "MM BIST primary core test result."
                  ::= { mmBistAndChassisStatus 25 }

      bistSecondaryCore OBJECT-TYPE
                  SYNTAX  INTEGER {
                    testSucceeded(0),
                    testFailed(1)
                  }
                  MAX-ACCESS  read-only
                  STATUS  current -- was mandatory
                  DESCRIPTION
                  "MM BIST secondary core test result."
                  ::= { mmBistAndChassisStatus 26 }

      bistInternalIOExpander OBJECT-TYPE
                  SYNTAX  INTEGER {
                    testSucceeded(0),
                    testFailed(1)
                  }
                  MAX-ACCESS  read-only
                  STATUS  current -- was mandatory
                  DESCRIPTION
                  "MM BIST internal IO expander test result."
                  ::= { mmBistAndChassisStatus 27 }

      bistRemoteControlFirmware OBJECT-TYPE
                  SYNTAX  INTEGER {
                    testSucceeded(0),
                    testFailed(1)
                  }
                  MAX-ACCESS  read-only
                  STATUS  current -- was mandatory
                  DESCRIPTION
                  "MM BIST Remote Control firmware test result."
                  ::= { mmBistAndChassisStatus 28 }

      bistPhysicalNetworkLink OBJECT-TYPE
                  SYNTAX  INTEGER {
                    testSucceeded(0),
                    testFailed(1)
                  }
                  MAX-ACCESS  read-only
                  STATUS  current -- was mandatory
                  DESCRIPTION
                  "MM BIST Physical Network Link test result."
                  ::= { mmBistAndChassisStatus 29 }

      bistLogicalNetworkLink OBJECT-TYPE
                  SYNTAX  INTEGER {
                    testSucceeded(0),
                    testFailed(1)
                  }
                  MAX-ACCESS  read-only
                  STATUS  current -- was mandatory
                  DESCRIPTION
                  "MM BIST Logical Network Link test result."
                  ::= { mmBistAndChassisStatus 30 }

      bistBladesInstalled OBJECT-TYPE
                  SYNTAX  OCTET STRING
                  MAX-ACCESS  read-only
                  STATUS  current -- was mandatory
                  DESCRIPTION
                  "The blades that are installed on the chassis.
                  The blades are listed as a bitmap.  The bitmap is a
                  string containing a list of 1's and 0's that is as long as
                  the number of blades supported.  If a blade is installed in a
                  bay, a 1 is present in the string in the position representing
                  the bay ID as read from left to right.  For example, if blades
                  are installed in bays 1, 5, and 13, and 14 blades are supported,
                  the string would look like '10001000000010'."
                  ::= { mmBistAndChassisStatus 33 }

      bistBladesCommunicating OBJECT-TYPE
                  SYNTAX  OCTET STRING
                  MAX-ACCESS  read-only
                  STATUS  current -- was mandatory
                  DESCRIPTION
                  "The blades that are communicating on the chassis.
                  The blades are listed as a bitmap.  The bitmap is a
                  string containing a list of 1's and 0's that is as long as
                  the number of blades supported.  If a blade installed in a
                  bay is communicating, a 1 is present in the string in the position
                  representing the bay ID as read from left to right.  For example,
                  if blades are communicating in bays 1, 5, and 13, and 14 blades
                  are supported, the string would look like '10001000000010'."
                  ::= { mmBistAndChassisStatus 49 }

      bistBlowersInstalled OBJECT-TYPE
                  SYNTAX  OCTET STRING
                  MAX-ACCESS  read-only
                  STATUS  current -- was mandatory
                  DESCRIPTION
                  "The blowers that are installed on the chassis.
                  The blowers are listed as a bitmap.  The bitmap is a
                  string containing a list of 1's and 0's that is as long as
                  the number of blowers supported.  If a blower is installed in a
                  bay, a 1 is present in the string in the position representing
                  the bay ID as read from left to right.  For example, if a blower
                  is installed in bay 1, and 2 blowers are supported, the string
                  would look like '10'.
                  
                  NOTE: Blowers are also referred to as Chassis Cooling Devices."
                  ::= { mmBistAndChassisStatus 65 }

      bistBlowersFunctional OBJECT-TYPE
                  SYNTAX  OCTET STRING
                  MAX-ACCESS  read-only
                  STATUS  current -- was mandatory
                  DESCRIPTION
                  "The blowers installed on the chassis that are functional.
                  The blowers are listed as a bitmap.  The bitmap is a
                  string containing a list of 1's and 0's that is as long as
                  the number of blowers supported.  If a blower is installed and
                  functional in a bay, a 1 is present in the string in the position
                  representing the bay ID as read from left to right.  For example,
                  if a blower is installed and functional only in bay 1, and 2 blowers
                  are supported, the string would look like '10'.

                  NOTE: Blowers are also referred to as Chassis Cooling Devices."
                  ::= { mmBistAndChassisStatus 73 }

      bistMediaTrayInstalled OBJECT-TYPE
                  SYNTAX  INTEGER {
                    no(0),
                    yes(1)
                  }
                  MAX-ACCESS  read-only
                  STATUS  current -- was mandatory
                  DESCRIPTION
                  "Indicates whether a media tray is installed on the chassis."
                  ::= { mmBistAndChassisStatus 74 }

      bistMediaTrayCommunicating OBJECT-TYPE
                  SYNTAX  INTEGER {
                    no(0),
                    yes(1)
                  }
                  MAX-ACCESS  read-only
                  STATUS  current -- was mandatory
                  DESCRIPTION
                  "Indicates whether a media tray is communicating."
                  ::= { mmBistAndChassisStatus 75 }

      bistOtherMMInstalled OBJECT-TYPE
                  SYNTAX  INTEGER {
                    no(0),
                    yes(1)
                  }
                  MAX-ACCESS  read-only
                  STATUS  current -- was mandatory
                  DESCRIPTION
                  "Indicates whether a redundant MM is installed."
                  ::= { mmBistAndChassisStatus 76 }

      bistOtherMMCommunicating OBJECT-TYPE
                  SYNTAX  INTEGER {
                    no(0),
                    yes(1)
                  }
                  MAX-ACCESS  read-only
                  STATUS  current -- was mandatory
                  DESCRIPTION
                  "Indicates whether a redundant MM is communicating."
                  ::= { mmBistAndChassisStatus 77 }

      bistPowerModulesInstalled OBJECT-TYPE
                  SYNTAX  OCTET STRING
                  MAX-ACCESS  read-only
                  STATUS  current -- was mandatory
                  DESCRIPTION
                  "The power modules that are installed on the chassis.
                  The power modules are listed as a bitmap.  The bitmap is a
                  string containing a list of 1's and 0's that is as long as
                  the number of power modules supported.  If a power module is
                  installed in a bay, a 1 is present in the string in the position
                  representing the bay ID as read from left to right.  For example,
                  if power modules are installed in bays 1 and 3, and 4 power modules
                  are supported, the string would look like '1010'."
                  ::= { mmBistAndChassisStatus 81 }

      bistPowerModulesFunctional OBJECT-TYPE
                  SYNTAX  OCTET STRING
                  MAX-ACCESS  read-only
                  STATUS  current -- was mandatory
                  DESCRIPTION
                  "The power modules that are functional on the chassis.
                  The power modules are listed as a bitmap.  The bitmap is a
                  string containing a list of 1's and 0's that is as long as
                  the number of power modules supported.  If a power module is
                  installed and functioning in a bay, a 1 is present in the string
                  in the position representing the bay ID as read from left to right.
                  For example, if power modules are installed and functioning in bays
                  1 and 3, and 4 power modules are supported, the string would look
                  like '1010'."
                  ::= { mmBistAndChassisStatus 89 }

      bistSwitchModulesInstalled OBJECT-TYPE
                  SYNTAX  OCTET STRING
                  MAX-ACCESS  read-only
                  STATUS  current -- was mandatory
                  DESCRIPTION
                  "The switch modules that are installed on the chassis.
                  The switch modules are listed as a bitmap.  The bitmap is a
                  string containing a list of 1's and 0's that is as long as
                  the number of switch modules supported.  If a switch module is
                  installed in a bay, a 1 is present in the string in the position
                  representing the bay ID as read from left to right.  For example,
                  if switch modules are installed in bays 1 and 3, and 4 switch modules
                  are supported, the string would look like '1011' for BladeCenter and 
                  BladeCenter T and '1011000000' for BladeCenter H and BladeCenter HT."
                  ::= { mmBistAndChassisStatus 97 }

      bistSwitchModulesCommunicating OBJECT-TYPE
                  SYNTAX  OCTET STRING
                  MAX-ACCESS  read-only
                  STATUS  current -- was mandatory
                  DESCRIPTION
                  "The switch modules that are communicating on the chassis.
                  The switch modules are listed as a bitmap.  The bitmap is a
                  string containing a list of 1's and 0's that is as long as
                  the number of switch modules supported.  If a switch module is
                  installed and functioning in a bay, a 1 is present in the string
                  in the position representing the bay ID as read from left to right.
                  For example, if switch modules are installed and functioning in bays
                  1 and 3, and 4 switch modules are supported, the string would look
                  like for BladeCenter and BladeCenter T and '1011000000' for 
                  BladeCenter H and BladeCenter HT."
                  ::= { mmBistAndChassisStatus 113 }

      bistLastUpdate OBJECT-TYPE
                  SYNTAX  OCTET STRING
                  MAX-ACCESS  read-only
                  STATUS  current -- was mandatory
                  DESCRIPTION
                  "It is the time when the primary MM updated the last BIST results."
                  ::= { mmBistAndChassisStatus 200 }

     rmmBistAndChassisStatus OBJECT IDENTIFIER ::= { spStatus 3 }

      rbistRs485Port1 OBJECT-TYPE
                  SYNTAX  INTEGER {
                    testSucceeded(0),
                    testFailed(1)
                  }
                  MAX-ACCESS  read-only
                  STATUS  current -- was mandatory
                  DESCRIPTION
                  "Standby MM BIST RS 485 legacy test result. The time of the last update 
                  can be obtained by querying rbistUpdateTime object."
                  ::= { rmmBistAndChassisStatus 2 }

      rbistRs485Port2 OBJECT-TYPE
                  SYNTAX  INTEGER {
                    testSucceeded(0),
                    testFailed(1)
                  }
                  MAX-ACCESS  read-only
                  STATUS  current -- was mandatory
                  DESCRIPTION
                  "Standby MM BIST RS 485 local bus test result. The time of the last update 
                  can be obtained by querying rbistUpdateTime object."
                  ::= { rmmBistAndChassisStatus 3 }

      rbistRtc OBJECT-TYPE
                  SYNTAX  INTEGER {
                    testSucceeded(0),
                    testFailed(1)
                  }
                  MAX-ACCESS  read-only
                  STATUS  current -- was mandatory
                  DESCRIPTION
                  "Standby MM BIST Real Time Clock test result. The time of the last update 
                  can be obtained by querying rbistUpdateTime object."
                  ::= { rmmBistAndChassisStatus 5 }

      rbistLocalI2CBus OBJECT-TYPE
                  SYNTAX  INTEGER {
                    testSucceeded(0),
                    testFailed(1)
                  }
                  MAX-ACCESS  read-only
                  STATUS  current -- was mandatory
                  DESCRIPTION
                  "Standby MM BIST Local I2C bus test result. The time of the last update 
                  can be obtained by querying rbistUpdateTime object."
                  ::= { rmmBistAndChassisStatus 7 }

      rbistPrimaryMainAppFlashImage  OBJECT-TYPE
                  SYNTAX  INTEGER {
                    testSucceeded(0),
                    testFailed(1)
                  }
                  MAX-ACCESS  read-only
                  STATUS  current -- was mandatory
                  DESCRIPTION
                  "Standby MM BIST Primary Main Application Firmware test result. 
                  The time of the last update can be obtained by querying rbistUpdateTime object."
                  ::= { rmmBistAndChassisStatus 8 }

      rbistSecondaryMainAppFlashImage  OBJECT-TYPE
                  SYNTAX  INTEGER {
                    testSucceeded(0),
                    testFailed(1)
                  }
                  MAX-ACCESS  read-only
                  STATUS  current -- was mandatory
                  DESCRIPTION
                  "Standby MM BIST Secondary Main Application test result. 
                  The time of the last update can be obtained by querying rbistUpdateTime object."
                  ::= { rmmBistAndChassisStatus 9 }

      rbistBootRomFlashImage  OBJECT-TYPE
                  SYNTAX  INTEGER {
                    testSucceeded(0),
                    testFailed(1)
                  }
                  MAX-ACCESS  read-only
                  STATUS  current -- was mandatory
                  DESCRIPTION
                  "Standby MM BIST Boot Firmware test result. The time of the last update 
                  can be obtained by querying rbistUpdateTime object."
                  ::= { rmmBistAndChassisStatus 10 }

      rbistEthernetPort1 OBJECT-TYPE
                  SYNTAX  INTEGER {
                    testSucceeded(0),
                    testFailed(1)
                  }
                  MAX-ACCESS  read-only
                  STATUS  current -- was mandatory
                  DESCRIPTION
                  "Standby MM BIST external ethernet port test result. The time of the last update 
                  can be obtained by querying rbistUpdateTime object."
                  ::= { rmmBistAndChassisStatus 11 }

      rbistExternalI2CDevices OBJECT-TYPE
                  SYNTAX  INTEGER {
                    testSucceeded(0),
                    testFailed(1)
                  }
                  MAX-ACCESS  read-only
                  STATUS  current -- was mandatory
                  DESCRIPTION
                  "Standby MM BIST external I2C devices test result collected 
                  when the standby MM was primary. The time of the last update 
                  can be obtained by querying rbistUpdateTimePrimary object."
                  ::= { rmmBistAndChassisStatus 14 }

      rbistInternalEthernetSwitch OBJECT-TYPE
                  SYNTAX  INTEGER {
                    testSucceeded(0),
                    testFailed(1)
                  }
                  MAX-ACCESS  read-only
                  STATUS  current -- was mandatory
                  DESCRIPTION
                  "Standby MM BIST internal external switch test result. 
                  The time of the last update can be obtained by querying rbistUpdateTime object."
                  ::= { rmmBistAndChassisStatus 19 }

      rbistVideoCapture OBJECT-TYPE
                  SYNTAX  INTEGER {
                    testSucceeded(0),
                    testFailed(1)
                  }
                  MAX-ACCESS  read-only
                  STATUS  current -- was mandatory
                  DESCRIPTION
                  "Standby MM BIST video capture test result collected 
                  when the standby MM was primary. The time of the last update 
                  can be obtained by querying rbistUpdateTimePrimary object."
                  ::= { rmmBistAndChassisStatus 20 }

      rbistUSBKeyboardMouseEmulation OBJECT-TYPE
                  SYNTAX  INTEGER {
                    testSucceeded(0),
                    testFailed(1)
                  }
                  MAX-ACCESS  read-only
                  STATUS  current -- was mandatory
                  DESCRIPTION
                  "Standby MM BIST USB keyboard and mouse test result collected 
                  when the standby MM was primary. The time of the last update 
                  can be obtained by querying rbistUpdateTimePrimary object."
                  ::= { rmmBistAndChassisStatus 21 }
                  
      rbistUSBMassStorageEmulation OBJECT-TYPE
                  SYNTAX  INTEGER {
                    testSucceeded(0),
                    testFailed(1)
                  }
                  MAX-ACCESS  read-only
                  STATUS  current -- was mandatory
                  DESCRIPTION
                  "Standby MM BIST mass storage emulation test result collected 
                  when the standby MM was primary. The time of the last update 
                  can be obtained by querying rbistUpdateTimePrimary object."
                  ::= { rmmBistAndChassisStatus 22 }
      
      rbistUSBKeyboardMouseFirmware OBJECT-TYPE
                  SYNTAX  INTEGER {
                    testSucceeded(0),
                    testFailed(1)
                  }
                  MAX-ACCESS  read-only
                  STATUS  current -- was mandatory
                  DESCRIPTION
                  "Standby MM BIST USB keyboard and mouse firmware test result 
                  collected when the standby MM was primary. The time of the last update 
                  can be obtained by querying rbistUpdateTimePrimary object."
                  ::= { rmmBistAndChassisStatus 23 }

      rbistUSBMassStorageFirmware OBJECT-TYPE
                  SYNTAX  INTEGER {
                    testSucceeded(0),
                    testFailed(1)
                  }
                  MAX-ACCESS  read-only
                  STATUS  current -- was mandatory
                  DESCRIPTION
                  "Standby MM BIST USB keyboard mouse firmware test result collected 
                  when the standby MM was primary. The time of the last update 
                  can be obtained by querying rbistUpdateTimePrimary object."
                  ::= { rmmBistAndChassisStatus 24 }

      rbistPrimaryCore OBJECT-TYPE
                  SYNTAX  INTEGER {
                    testSucceeded(0),
                    testFailed(1)
                  }
                  MAX-ACCESS  read-only
                  STATUS  current -- was mandatory
                  DESCRIPTION
                  "Standby MM BIST primary core test result. The time of the last update 
                  can be obtained by querying rbistUpdateTime object."
                  ::= { rmmBistAndChassisStatus 25 }

      rbistSecondaryCore OBJECT-TYPE
                  SYNTAX  INTEGER {
                    testSucceeded(0),
                    testFailed(1)
                  }
                  MAX-ACCESS  read-only
                  STATUS  current -- was mandatory
                  DESCRIPTION
                  "Standby MM BIST secondary core test result. The time of the last update 
                  can be obtained by querying rbistUpdateTime object."
                  ::= { rmmBistAndChassisStatus 26 }

      rbistInternalIOExpander OBJECT-TYPE
                  SYNTAX  INTEGER {
                    testSucceeded(0),
                    testFailed(1)
                  }
                  MAX-ACCESS  read-only
                  STATUS  current -- was mandatory
                  DESCRIPTION
                  "Standby MM BIST internal IO expander test result. The time of the last update 
                  can be obtained by querying rbistUpdateTime object."
                  ::= { rmmBistAndChassisStatus 27 }

      rbistRemoteControlFirmware OBJECT-TYPE
                  SYNTAX  INTEGER {
                    testSucceeded(0),
                    testFailed(1)
                  }
                  MAX-ACCESS  read-only
                  STATUS  current -- was mandatory
                  DESCRIPTION
                  "Standby MM BIST Remote Control firmware test result collected 
                  when the standby MM was primary. The time of the last update 
                  can be obtained by querying rbistUpdateTimePrimary object."
                  ::= { rmmBistAndChassisStatus 28 }

      rbistPhysicalNetworkLink OBJECT-TYPE
                  SYNTAX  INTEGER {
                    testSucceeded(0),
                    testFailed(1)
                  }
                  MAX-ACCESS  read-only
                  STATUS  current -- was mandatory
                  DESCRIPTION
                  "Standby MM BIST Physical Network Link test result collected 
                  when the standby MM was primary. The time of the last update 
                  can be obtained by querying rbistUpdateTimePrimary object."
                  ::= { rmmBistAndChassisStatus 29 }

      rbistLogicalNetworkLink OBJECT-TYPE
                  SYNTAX  INTEGER {
                    testSucceeded(0),
                    testFailed(1)
                  }
                  MAX-ACCESS  read-only
                  STATUS  current -- was mandatory
                  DESCRIPTION
                  "Standby MM BIST Logical Network Link test result collected 
                  when the standby MM was primary. The time of the last update 
                  can be obtained by querying rbistUpdateTimePrimary object."
                  ::= { rmmBistAndChassisStatus 30 }

      rbistBladesInstalled OBJECT-TYPE
                  SYNTAX  OCTET STRING
                  MAX-ACCESS  read-only
                  STATUS  current -- was mandatory
                  DESCRIPTION
                  "The blades that were installed on the chassis when the 
                  standby MM was once primary. The time of the last update 
                  can be obtained by querying rbistUpdateTimePrimary object.
                  The blades are listed as a bitmap.  The bitmap is a
                  string containing a list of 1's and 0's that is as long as
                  the number of blades supported.  If a blade is installed in a
                  bay, a 1 is present in the string in the position representing
                  the bay ID as read from left to right.  For example, if blades
                  are installed in bays 1, 5, and 13, and 14 blades are supported,
                  the string would look like '10001000000010'. "
                  ::= { rmmBistAndChassisStatus 33 }

      rbistBladesCommunicating OBJECT-TYPE
                  SYNTAX  OCTET STRING
                  MAX-ACCESS  read-only
                  STATUS  current -- was mandatory
                  DESCRIPTION
                  "The blades that were communicating on the chassis when the 
                  standby MM was once primary. The time of the last update 
                  can be obtained by querying rbistUpdateTimePrimary object.
                  The blades are listed as a bitmap.  The bitmap is a
                  string containing a list of 1's and 0's that is as long as
                  the number of blades supported.  If a blade installed in a
                  bay is communicating, a 1 is present in the string in the position
                  representing the bay ID as read from left to right.  For example,
                  if blades are communicating in bays 1, 5, and 13, and 14 blades
                  are supported, the string would look like '10001000000010'."
                  ::= { rmmBistAndChassisStatus 49 }

      rbistBlowersInstalled OBJECT-TYPE
                  SYNTAX  OCTET STRING
                  MAX-ACCESS  read-only
                  STATUS  current -- was mandatory
                  DESCRIPTION
                  "The blowers that were installed on the chassis when the 
                  standby MM was once primary. The time of the last update 
                  can be obtained by querying rbistUpdateTimePrimary object.
                  The blowers are listed as a bitmap.  The bitmap is a
                  string containing a list of 1's and 0's that is as long as
                  the number of blowers supported.  If a blower is installed in a
                  bay, a 1 is present in the string in the position representing
                  the bay ID as read from left to right.  For example, if a blower
                  is installed in bay 1, and 2 blowers are supported, the string
                  would look like '10'.

                  NOTE: Blowers are also referred to as Chassis Cooling Devices."
                  ::= { rmmBistAndChassisStatus 65 }

      rbistBlowersFunctional OBJECT-TYPE
                  SYNTAX  OCTET STRING
                  MAX-ACCESS  read-only
                  STATUS  current -- was mandatory
                  DESCRIPTION
                  "The blowers installed on the chassis that were functional when the 
                  standby MM was once primary. The time of the last update 
                  can be obtained by querying rbistUpdateTimePrimary object.
                  The blowers are listed as a bitmap.  The bitmap is a
                  string containing a list of 1's and 0's that is as long as
                  the number of blowers supported.  If a blower is installed and
                  functional in a bay, a 1 is present in the string in the position
                  representing the bay ID as read from left to right.  For example,
                  if a blower is installed and functional only in bay 1, and 2 blowers
                  are supported, the string would look like '10'.

                  NOTE: Blowers are also referred to as Chassis Cooling Devices."
                  ::= { rmmBistAndChassisStatus 73 }

      rbistMediaTrayInstalled OBJECT-TYPE
                  SYNTAX  INTEGER {
                    no(0),
                    yes(1)
                  }
                  MAX-ACCESS  read-only
                  STATUS  current -- was mandatory
                  DESCRIPTION
                  "Indicates whether a media tray was installed on the chassis when the 
                  standby MM was once primary. The time of the last update 
                  can be obtained by querying rbistUpdateTimePrimary object."
                  ::= { rmmBistAndChassisStatus 74 }

      rbistMediaTrayCommunicating OBJECT-TYPE
                  SYNTAX  INTEGER {
                    no(0),
                    yes(1)
                  }
                  MAX-ACCESS  read-only
                  STATUS  current -- was mandatory
                  DESCRIPTION
                  "Indicates whether a media tray was communicating when the 
                  standby MM was once primary. The time of the last update 
                  can be obtained by querying rbistUpdateTimePrimary object."
                  ::= { rmmBistAndChassisStatus 75 }

      rbistOtherMMInstalled OBJECT-TYPE
                  SYNTAX  INTEGER {
                    no(0),
                    yes(1)
                  }
                  MAX-ACCESS  read-only
                  STATUS  current -- was mandatory
                  DESCRIPTION
                  "Indicates whether a standby MM was installed when the 
                  standby MM was once primary.The time of the last update 
                  can be obtained by querying rbistUpdateTimePrimary object."
                  ::= { rmmBistAndChassisStatus 76 }

      rbistOtherMMCommunicating OBJECT-TYPE
                  SYNTAX  INTEGER {
                    no(0),
                    yes(1)
                  }
                  MAX-ACCESS  read-only
                  STATUS  current -- was mandatory
                  DESCRIPTION
                  "Indicates whether a standby MM was communicating when the 
                  standby MM was once primary. The time of the last update can be
                  gotten from the object 'rbistUpdateTimePrimary'."
                  ::= { rmmBistAndChassisStatus 77 }

      rbistPowerModulesInstalled OBJECT-TYPE
                  SYNTAX  OCTET STRING
                  MAX-ACCESS  read-only
                  STATUS  current -- was mandatory
                  DESCRIPTION
                  "The power modules that were installed on the chassis when the 
                  standby MM was once primary. The time of the last update 
                  can be obtained by querying rbistUpdateTimePrimary object.
                  The power modules are listed as a bitmap.  The bitmap is a
                  string containing a list of 1's and 0's that is as long as
                  the number of power modules supported.  If a power module was
                  installed in a bay, a 1 is present in the string in the position
                  representing the bay ID as read from left to right.  For example,
                  if power modules were installed in bays 1 and 3, and 4 power modules
                  were supported, the string would look like '1010'."
                  ::= { rmmBistAndChassisStatus 81 }

      rbistPowerModulesFunctional OBJECT-TYPE
                  SYNTAX  OCTET STRING
                  MAX-ACCESS  read-only
                  STATUS  current -- was mandatory
                  DESCRIPTION
                  "The power modules that were functional on the chassis when the 
                  standby MM was once primary. The time of the last update 
                  can be obtained by querying rbistUpdateTimePrimary object.
                  The power modules are listed as a bitmap.  The bitmap is a
                  string containing a list of 1's and 0's that is as long as
                  the number of power modules supported.  If a power module was
                  installed and functioning in a bay, a 1 is present in the string
                  in the position representing the bay ID as read from left to right.
                  For example, if power modules were installed and functioning in bays
                  1 and 3, and 4 power modules were supported, the string would look
                  like '1010'."
                  ::= { rmmBistAndChassisStatus 89 }

      rbistSwitchModulesInstalled OBJECT-TYPE
                  SYNTAX  OCTET STRING
                  MAX-ACCESS  read-only
                  STATUS  current -- was mandatory
                  DESCRIPTION
                  "The switch modules that were installed on the chassis when the 
                  standby MM was once primary. The time of the last update 
                  can be obtained by querying rbistUpdateTimePrimary object.
                  The switch modules are listed as a bitmap.  The bitmap is a
                  string containing a list of 1's and 0's that is as long as
                  the number of switch modules supported.  If a switch module was
                  installed in a bay, a 1 is present in the string in the position
                  representing the bay ID as read from left to right.  For example,
                  if switch modules were installed in bays 1 and 3, and 4 switch modules
                  were supported, the string would look like '1011' for BladeCenter and 
                  BladeCenter T and '1011000000' for BladeCenter H and BladeCenter HT."
                  ::= { rmmBistAndChassisStatus 97 }

      rbistSwitchModulesCommunicating OBJECT-TYPE
                  SYNTAX  OCTET STRING
                  MAX-ACCESS  read-only
                  STATUS  current -- was mandatory
                  DESCRIPTION
                  "The switch modules that are communicating on the chassis when the 
                  standby MM was once primary. The time of the last update 
                  can be obtained by querying rbistUpdateTimePrimary object.
                  The switch modules are listed as a bitmap.  The bitmap is a
                  string containing a list of 1's and 0's that is as long as
                  the number of switch modules supported.  If a switch module was
                  installed and functioning in a bay, a 1 is present in the string
                  in the position representing the bay ID as read from left to right.
                  For example, if switch modules were installed and functioning in bays
                  1 and 3, and 4 switch modules were supported, the string would look
                  like for BladeCenter and BladeCenter T and '1011000000' for 
                  BladeCenter H and BladeCenter HT."
                  ::= { rmmBistAndChassisStatus 113 }

      rbistUpdateTime OBJECT-TYPE
                  SYNTAX  OCTET STRING
                  MAX-ACCESS  read-only
                  STATUS  current -- was mandatory
                  DESCRIPTION
                  "It is the time when the standby MM updated the last BIST results."
                  ::= { rmmBistAndChassisStatus 200 }

      rbistLastUpdatePrimary OBJECT-TYPE
                  SYNTAX  OCTET STRING
                  MAX-ACCESS  read-only
                  STATUS  current -- was mandatory
                  DESCRIPTION
                  "It is the time when the standby MM updated the last BIST results 
                   when it was still primary."
                  ::= { rmmBistAndChassisStatus 201 }

    -- ********************************************************************************
    -- Fan Pack Health State
    -- ********************************************************************************
    fanPack OBJECT IDENTIFIER ::= { monitors 6 }
    
      fanPackTable OBJECT-TYPE
                  SYNTAX  SEQUENCE OF FanPackEntry
                  MAX-ACCESS  not-accessible
                  STATUS  current -- was mandatory
                  DESCRIPTION
                  "Table of fan pack information.  Contains
                  the information for each fan pack.

                  NOTE: Fan packs are also referred to as Power Module Cooling Devices."
                  ::= { fanPack 1 }

       fanPackEntry OBJECT-TYPE
                  SYNTAX FanPackEntry
                  MAX-ACCESS  not-accessible
                  STATUS  current -- was mandatory
                  DESCRIPTION
                  "Fan Pack entry"
                  INDEX { fanPackIndex }
                  ::= { fanPackTable 1 }


       FanPackEntry ::= SEQUENCE {
                  fanPackIndex INTEGER,
                  fanPackExists INTEGER,
                  fanPackState INTEGER,
                  fanPackFanCount INTEGER,
                  fanPackAverageSpeed OCTET STRING, 
                  fanPackAverageSpeedRPM OCTET STRING, 
                  fanPackControllerState INTEGER
                  }

       fanPackIndex  OBJECT-TYPE
                  SYNTAX  Integer32 (0..2147483647) -- was INTEGER
                  MAX-ACCESS  read-only
                  STATUS  current -- was mandatory
                  DESCRIPTION
                  "Fan Pack sequence index."
                  ::= { fanPackEntry 1 }
                   
       fanPackExists OBJECT-TYPE
                  SYNTAX  INTEGER {
                    false(0),
                    true(1)
                  }
                  MAX-ACCESS  read-only
                  STATUS  current -- was mandatory
                  DESCRIPTION
                  "Indicates whether the fan pack specified exists or not."
                  ::= { fanPackEntry 2 }

       fanPackState OBJECT-TYPE
                  SYNTAX  INTEGER {
                    unknown(0),
                    good(1),
                    warning(2),
                    bad(3)
                  }
                  MAX-ACCESS  read-only
                  STATUS  current -- was mandatory
                  DESCRIPTION
                  "The health state for the fan pack.
                  0 = unknown, 1 = good, 2 = warning, 3 = bad."
                  ::= { fanPackEntry 3}

       fanPackFanCount OBJECT-TYPE
                  SYNTAX  INTEGER {
                    unknown(255)
                  }
                  MAX-ACCESS  read-only
                  STATUS  current -- was mandatory
                  DESCRIPTION
                  "The number of fans in the fan pack."
                  ::= { fanPackEntry 4 }

       fanPackAverageSpeed    OBJECT-TYPE
                  SYNTAX  OCTET STRING
                  MAX-ACCESS  read-only
                  STATUS  current -- was mandatory
                  DESCRIPTION
                  "The average speed of all fans in the fan pack expressed in percent(%) 
                  of maximum RPM. If the fan pack is determined not to be running or
                  the fan pack speed cannot be determined, the string will
                  indicate 'Offline'.  The string 'Not Readable!' indicates that the 
                  given monitor is not supported on this system."
                  ::= { fanPackEntry 5 }

       fanPackAverageSpeedRPM    OBJECT-TYPE
                  SYNTAX  OCTET STRING
                  MAX-ACCESS  read-only
                  STATUS  current -- was mandatory
                  DESCRIPTION
                  "The average speed of all fans in the fan pack expressed in RPM.  
                  If the fan pack is determined not to be running or the fan pack speed 
                  cannot be determined, the string will indicate 'Offline'. The string 
                  'Not Readable!' indicates that the given monitor is not supported on 
                  this system."
                  ::= { fanPackEntry 6 }
                  
       fanPackControllerState    OBJECT-TYPE
                  SYNTAX  INTEGER {
                     operational(0),
                     flashing(1),
                     notPresent(2),
                     communicationError(3), 
                     unknown(255)
                  }
                  MAX-ACCESS  read-only
                  STATUS  current -- was mandatory
                  DESCRIPTION
                  "The health state for the controller for the fan pack.
                  0 = operational, 1 = flashing in progress, 2 = not present, 3 = communication error, 
                  255 = unknown"
                  ::= { fanPackEntry 7}

    -- ********************************************************************************
    -- System Health
    -- ********************************************************************************
    systemHealth OBJECT IDENTIFIER ::= { monitors 7 }

     -- ********************************************************************************
     -- System Health Status
     -- ********************************************************************************
     systemHealthStat  OBJECT-TYPE
                  SYNTAX  INTEGER {
                                    critical(0),
                                    nonCritical(2),
                                    systemLevel(4),
                                    normal(255)
                                  }
                  MAX-ACCESS  read-only
                  STATUS  current -- was mandatory
                  DESCRIPTION
                  "Indicates status of system health for the
                  system in which the MM resides.
                  Value of 'critical' indicates a severe error has occurred
                  and the system may not be functioning. A value of
                  'nonCritical' indicates that a error has occurred but
                  the system is currently functioning properly.  A value of
                  'systemLevel' indicates that a condition has occurred
                  that may change the state of the system in the future but currently
                  the system is working properly. A value of
                  'normal' indicates that the system is operating normally."
                  ::= { systemHealth 1 }

     -- ********************************************************************************
     -- System Health Summary
     -- ********************************************************************************
     systemHealthSummaryTable OBJECT-TYPE
                   SYNTAX  SEQUENCE OF SystemHealthSummaryEntry
                   MAX-ACCESS  not-accessible
                   STATUS  current -- was mandatory
                   DESCRIPTION
                   "Table of System Health summary. Contains more detailed
                   information about the reasons for the overall system
                   health status.
                   
                   NOTE: This MIB object is for BladeCenter only."
                   ::= { systemHealth 2 }

     systemHealthSummaryEntry OBJECT-TYPE
                   SYNTAX SystemHealthSummaryEntry
                   MAX-ACCESS  not-accessible
                   STATUS  current -- was mandatory
                   DESCRIPTION
                   "System Health Summary entry
                   
                   NOTE: This MIB object is for BladeCenter only."
                   INDEX { systemHealthSummaryIndex }
                   ::= { systemHealthSummaryTable 1 }


     SystemHealthSummaryEntry ::= SEQUENCE {
                 systemHealthSummaryIndex INTEGER,
                 systemHealthSummarySeverity OCTET STRING,
                 systemHealthSummaryDescription OCTET STRING
                 }


     systemHealthSummaryIndex  OBJECT-TYPE
                 SYNTAX  Integer32 (0..2147483647) -- was INTEGER
                 MAX-ACCESS  read-only
                 STATUS  current -- was mandatory
                 DESCRIPTION
                 "System health summary index.
                 
                 NOTE: This MIB object is for BladeCenter only."
                 ::= { systemHealthSummaryEntry 1 }

     systemHealthSummarySeverity  OBJECT-TYPE
                 SYNTAX  OCTET STRING
                 MAX-ACCESS  read-only
                 STATUS  current -- was mandatory
                 DESCRIPTION
                 "System health summary severity.
                 
                 NOTE: This MIB object is for BladeCenter only."
                 ::= { systemHealthSummaryEntry 2 }

     systemHealthSummaryDescription  OBJECT-TYPE
                 SYNTAX  OCTET STRING
                 MAX-ACCESS  read-only
                 STATUS  current -- was mandatory
                 DESCRIPTION
                 "System health summary description.
                 
                 NOTE: This MIB object is for BladeCenter only."
                 ::= { systemHealthSummaryEntry 3 }

    -- ********************************************************************************
    -- LEDs
    -- ********************************************************************************
    leds OBJECT IDENTIFIER ::= { monitors 8 }

     -- ********************************************************************************
     -- Front Panel LEDs
     -- ********************************************************************************
     frontPanelLEDs OBJECT IDENTIFIER ::= { leds 1 }


      systemErrorLED OBJECT-TYPE
                   SYNTAX INTEGER {
                     off(0),
                     on(1)
                   }
                   MAX-ACCESS  read-only
                   STATUS  current -- was mandatory
                   DESCRIPTION
                   "Indicates whether the front panel system error LED is on or off.
                   
                   NOTE: This MIB object is for BladeCenter only."
                   ::= { frontPanelLEDs 1 }


      informationLED OBJECT-TYPE
                   SYNTAX INTEGER {
                     off(0),
                     on(1)
                   }
                   MAX-ACCESS  read-write
                   STATUS  current -- was mandatory
                   DESCRIPTION
                   "Indicates whether the front panel system information LED
                   is on or off.  For Write access, the LED can be turned off 
                   only.
                   
                   NOTE: This MIB object is for BladeCenter only."
                   ::= { frontPanelLEDs 2 }


      temperatureLED OBJECT-TYPE
                   SYNTAX INTEGER {
                     off(0),
                     on(1)
                   }
                   MAX-ACCESS  read-only
                   STATUS  current -- was mandatory
                   DESCRIPTION
                   "Indicates whether the front panel temperature LED is on or off.
                   
                   NOTE: This MIB object is for BladeCenter only."
                   ::= { frontPanelLEDs 3 }


      identityLED OBJECT-TYPE
                   SYNTAX INTEGER {
                     off(0),
                     on(1),
                     blinking(2),
                     notAvailable(3)
                   }
                   MAX-ACCESS  read-write
                   STATUS  current -- was mandatory
                   DESCRIPTION
                   "Indicates whether the front panel identity LED is on or off.
                   
                   NOTE: This MIB object is for BladeCenter only."
                   ::= { frontPanelLEDs 4 }


     -- ********************************************************************************
     -- Blade LEDs
     -- ********************************************************************************
     bladeLEDs OBJECT IDENTIFIER ::= { leds 2 }

      bladeLEDsTable OBJECT-TYPE
                    SYNTAX  SEQUENCE OF BladeLEDsEntry
                    MAX-ACCESS  not-accessible
                    STATUS  current -- was mandatory
                    DESCRIPTION
                    "Table of blade status information."
                    ::= { bladeLEDs 1 }

       bladeLEDsEntry OBJECT-TYPE
                     SYNTAX BladeLEDsEntry
                     MAX-ACCESS  not-accessible
                     STATUS  current -- was mandatory
                     DESCRIPTION
                     "Blade system status entry"
                     INDEX { bladeStatusIndex }
                     ::= { bladeLEDsTable 1 }


       BladeLEDsEntry ::= SEQUENCE {
                   ledBladeIndex INTEGER,
                   ledBladeId INTEGER,
                   ledBladeExists INTEGER,
                   ledBladePowerState INTEGER,
                   ledBladeHealthState INTEGER,
                   ledBladeName OCTET STRING,
                   ledBladeSystemError INTEGER,
                   ledBladeInformation INTEGER,
                   ledBladeKVM INTEGER,
                   ledBladeMediaTray INTEGER,
                   ledBladeIdentity INTEGER
                   }


       ledBladeIndex OBJECT-TYPE
                   SYNTAX  Integer32 (0..2147483647) -- was INTEGER
                   MAX-ACCESS  read-only
                   STATUS  current -- was mandatory
                   DESCRIPTION
                   "Blade LED table index."
                   ::= { bladeLEDsEntry 1 }

       ledBladeId OBJECT-TYPE
                   SYNTAX  INTEGER {
                       blade1(1),
                       blade2(2),
                       blade3(3),
                       blade4(4),
                       blade5(5),
                       blade6(6),
                       blade7(7),
                       blade8(8),
                       blade9(9),
                       blade10(10),
                       blade11(11),
                       blade12(12),
                       blade13(13),
                       blade14(14)
                   }
                   MAX-ACCESS  read-only
                   STATUS  current -- was mandatory
                   DESCRIPTION
                   "The numeric blade ID."
                   ::= { bladeLEDsEntry 2 }

       ledBladeExists OBJECT-TYPE
                   SYNTAX  INTEGER {
                     false(0),
                     true(1)
                   }
                   MAX-ACCESS  read-only
                   STATUS  current -- was mandatory
                   DESCRIPTION
                   "Indicates whether the server blade specified exists or not."
                   ::= { bladeLEDsEntry 3 }

       ledBladePowerState  OBJECT-TYPE
                   SYNTAX  INTEGER {
                     off(0),
                     on(1),
                     standby(3),
                     hibernate(4)
                   }
                   MAX-ACCESS  read-only
                   STATUS  current -- was mandatory
                   DESCRIPTION
                   "Indicates the power state of the blade specified."
                   ::= { bladeLEDsEntry 4 }

       ledBladeHealthState  OBJECT-TYPE
                   SYNTAX  INTEGER {
                     unknown(0),
                     good(1),
                     warning(2),
                     critical(3),
                     kernelMode(4),
                     discovering(5),
                     commError(6),
                     noPower(7),
                     flashing(8),
                     initFailure(9),
                     insufficientPower(10),
                     powerDenied(11)
                   }
                   MAX-ACCESS  read-only
                   STATUS  current -- was mandatory
                   DESCRIPTION
                   "The system health state for the blade.

                    Unknown: Blade is in an undefined state.
                    Good: Blade is operating normally.
                    Warning: One or more outstanding warnings exist for this blade.
                    Critical: One or more outstanding critical events for this blade.
                    Kernel Mode: Blade is in kernel mode.
                    Discovering: The AMM is currently in the process of discovering this blade.
                    Communications Error: The AMM failed to communicate with this blade.
                    No Power: No power to the blade's domain.
                    Flashing: Flashing in progress.
                    Initialization Failure: Blade failed to initialized.
                    Insufficient Power: Not enough power is left in the blade's domain to power the blade.
                    Power Denied: Power was denied to the blade."
                   ::= { bladeLEDsEntry 5 }

       ledBladeName OBJECT-TYPE
                   SYNTAX  OCTET STRING
                   MAX-ACCESS  read-only
                   STATUS  current -- was mandatory
                   DESCRIPTION
                   "The name of the blade as a null terminated string."
                   ::= { bladeLEDsEntry 6 }

       ledBladeSystemError  OBJECT-TYPE
                   SYNTAX  INTEGER {
                     off(0),
                     on(1)
                   }
                   MAX-ACCESS  read-only
                   STATUS  current -- was mandatory
                   DESCRIPTION
                   "Indicates whether the blade system error LED is on or off."
                   ::= { bladeLEDsEntry 7 }

       ledBladeInformation  OBJECT-TYPE
                   SYNTAX  INTEGER {
                     off(0),
                     on(1)
                   }
                   MAX-ACCESS  read-write
                   STATUS  current -- was mandatory
                   DESCRIPTION
                   "Indicates whether the blade information LED is on or off.  
                   For Write access, the LED can be turned off only."
                   ::= { bladeLEDsEntry 8 }

       ledBladeKVM  OBJECT-TYPE
                   SYNTAX  INTEGER {
                     off(0),
                     on(1),
                     blinking(2)
                   }
                   MAX-ACCESS  read-only
                   STATUS  current -- was mandatory
                   DESCRIPTION
                   "Indicates whether the blade KVM LED is on, off, or blinking."
                   ::= { bladeLEDsEntry 9 }

       ledBladeMediaTray  OBJECT-TYPE
                   SYNTAX  INTEGER {
                     off(0),
                     on(1),
                     blinking(2)
                   }
                   MAX-ACCESS  read-only
                   STATUS  current -- was mandatory
                   DESCRIPTION
                   "Indicates whether the blade media tray LED is on, off, or blinking."
                   ::= { bladeLEDsEntry 10 }

       ledBladeIdentity OBJECT-TYPE
                   SYNTAX  INTEGER {
                     off(0),
                     on(1),
                     blinking(2)
                   }
                   MAX-ACCESS  read-write
                   STATUS  current -- was mandatory
                   DESCRIPTION
                   "Indicates whether the blade identify LED is on, off, or blinking."
                   ::= { bladeLEDsEntry 11 }

      bladeLEDsDetailsTable OBJECT-TYPE
                    SYNTAX  SEQUENCE OF BladeLEDsDetailsEntry
                    MAX-ACCESS  not-accessible
                    STATUS  current -- was mandatory
                    DESCRIPTION
                    "Table of blade LEDs detailed information."
                    ::= { bladeLEDs 2 }

       bladeLEDsDetailsEntry OBJECT-TYPE
                     SYNTAX  BladeLEDsDetailsEntry
                     MAX-ACCESS  not-accessible
                     STATUS  current -- was mandatory
                     DESCRIPTION
                     "Blade LEDs Details entry"
                     INDEX { ledIndex }
                     ::= { bladeLEDsDetailsTable 1 }

       BladeLEDsDetailsEntry ::= SEQUENCE {
                   ledIndex INTEGER,
                   ledBladeBayNumber OCTET STRING,
                   ledBladeComponentType OCTET STRING,
                   ledBladeLabel OCTET STRING,
                   ledBladeState INTEGER,
                   ledBladeLocation OCTET STRING
                   }
       
       ledIndex  OBJECT-TYPE
                  SYNTAX  Integer32 (0..2147483647) -- was INTEGER
                  MAX-ACCESS  read-only
                  STATUS  current -- was mandatory
                  DESCRIPTION
                  "The LED index number.  
                  For consistent results, view as a table and not as individual entries."
                  ::= { bladeLEDsDetailsEntry 1 }
                         
       ledBladeBayNumber  OBJECT-TYPE
                  SYNTAX  OCTET STRING
                  MAX-ACCESS  read-only
                  STATUS  current -- was mandatory
                  DESCRIPTION
                  "The bay number of the main server blade that the LED is grouped into.
                  For consistent results, view as a table and not as individual entries."
                  ::= { bladeLEDsDetailsEntry 2 }
                    
       ledBladeComponentType OBJECT-TYPE
                  SYNTAX  OCTET STRING
                  MAX-ACCESS  read-only
                  STATUS  current -- was mandatory
                  DESCRIPTION
                  "Type of the component/subcomponent grouping for this LED.
                  For consistent results, view as a table and not as individual entries."
                  ::= { bladeLEDsDetailsEntry 3 }
      
       ledBladeLabel OBJECT-TYPE
                  SYNTAX  OCTET STRING
                  MAX-ACCESS  read-only
                  STATUS  current -- was mandatory
                  DESCRIPTION
                  "Text label for a LED.  
                  For consistent results, view as a table and not as individual entries."
                  ::= { bladeLEDsDetailsEntry 4 }

       ledBladeState OBJECT-TYPE
                  SYNTAX  INTEGER {
                     off(0),
                     on(1),
                     blinking(2)
                   }
                  MAX-ACCESS  read-only
                  STATUS  current -- was mandatory
                  DESCRIPTION
                  "Text description which denotes color or on/off/blink state for a LED.
                  For consistent results, view as a table and not as individual entries."
                  ::= { bladeLEDsDetailsEntry 5 }

       ledBladeLocation OBJECT-TYPE
                  SYNTAX  OCTET STRING
                  MAX-ACCESS  read-only
                  STATUS  current -- was mandatory
                  DESCRIPTION
                  "Location of this LED.  
                  For consistent results, view as a table and not as individual entries."
                  ::= { bladeLEDsDetailsEntry 6 }

     -- ***********************************************************************
     -- BladeCenter T Panel LEDs
     -- ***********************************************************************
     telcoPanelLEDs OBJECT IDENTIFIER ::= { leds 3 }


     criticalLED   OBJECT-TYPE
                   SYNTAX INTEGER {
                     off(0),
                     on(1)
                   }
                   MAX-ACCESS  read-only
                   STATUS  current -- was mandatory
                   DESCRIPTION
                   "Indicates whether the BladeCenter T Panel CRT (Critical) LED is on or off.
                   
                   NOTE: This MIB object is for BladeCenter T only."
                   ::= { telcoPanelLEDs 1 }


     majorLED      OBJECT-TYPE
                   SYNTAX INTEGER {
                     off(0),
                     on(1)
                   }
                   MAX-ACCESS  read-only
                   STATUS  current -- was mandatory
                   DESCRIPTION
                   "Indicates whether the BladeCenter T Panel MJR (Major) LED is on or off.
                   
                   NOTE: This MIB object is for BladeCenter T only."
                   ::= { telcoPanelLEDs 2 }

     minorLED      OBJECT-TYPE
                   SYNTAX INTEGER {
                     off(0),
                     on(1)
                   }
                   MAX-ACCESS  read-only
                   STATUS  current -- was mandatory
                   DESCRIPTION
                   "Indicates whether the BladeCenter T Panel MNR (Minor) LED is on or off.
                   
                   NOTE: This MIB object is for BladeCenter T only."
                   ::= { telcoPanelLEDs 3 }


     telcoIdentityLED OBJECT-TYPE
                   SYNTAX INTEGER {
                     off(0),
                     on(1),
                     blinking(2),
                     notAvailable(3)
                   }
                   MAX-ACCESS  read-write
                   STATUS  current -- was mandatory
                   DESCRIPTION
                   "Indicates whether the BladeCenter T Panel identity LED is on or off.
                   
                   NOTE: This MIB object is for BladeCenter T only."
                   ::= { telcoPanelLEDs 4 }
    
 
     telcoColorSel OBJECT-TYPE
                   SYNTAX INTEGER {
                     amber(0),
                     red(1)
                   }
                   MAX-ACCESS  read-write
                   STATUS  current -- was mandatory
                   DESCRIPTION
                   "Indicates whether the BladeCenter T Critical and Major LEDs are displayed in amber or red color.
                   
                   NOTE: This MIB object is for BladeCenter T only."
                   ::= { telcoPanelLEDs 5 }



     criticalityAssertionMode OBJECT-TYPE
                   SYNTAX INTEGER {
                     disable(0),
                     enable(1)
                   }
                   MAX-ACCESS  read-write
                   STATUS  current -- was mandatory
                   DESCRIPTION
                   "Indicates whether the BladeCenter T Criticality Assertion Mode is enabled or disabled.
                   
                   NOTE: This MIB object is for BladeCenter T only."
                   ::= { telcoPanelLEDs 6 }



     -- ********************************************************************************
     -- Switch Module LEDs
     -- ********************************************************************************
     smLEDs OBJECT IDENTIFIER ::= { leds 4 }

      smLEDsTable   OBJECT-TYPE
                    SYNTAX  SEQUENCE OF SMLEDsEntry
                    MAX-ACCESS  not-accessible
                    STATUS  current -- was mandatory
                    DESCRIPTION
                    "Table of switch module LEDs information."
                    ::= { smLEDs 1 }

       smLEDsEntry   OBJECT-TYPE
                     SYNTAX SMLEDsEntry
                     MAX-ACCESS  not-accessible
                     STATUS  current -- was mandatory
                     DESCRIPTION
                     "Switch module LEDs information entry"
                     INDEX { ledSMIndex }
                     ::= { smLEDsTable 1 }


       SMLEDsEntry ::= SEQUENCE {
                   ledSMIndex INTEGER,
                   ledSMLEDs  OCTET STRING  
                   }


       ledSMIndex  OBJECT-TYPE
                   SYNTAX  INTEGER (0..128)
                   MAX-ACCESS  read-only
                   STATUS  current -- was mandatory
                   DESCRIPTION
                   "Switch module LEDs table index.  "
                   ::= { smLEDsEntry 1 }

       ledSMLEDs   OBJECT-TYPE
                   SYNTAX  OCTET STRING (SIZE(256))
                   MAX-ACCESS  read-only
                   STATUS  current -- was mandatory
                   DESCRIPTION
                   "A bitmap of LEDs information on the selected switch module.  The 
                   bitmap is a string containing a list of 1's and 0's.  Every 4 bytes
                   are used to represent a led state. The first 64 bytes represent the 
                   status of the external LEDs while the last 64 bytes represent the 
                   status of the internal port connections from the switch module to 
                   blades.  Each nibble of data is presented in the bitmap format (0000) 
                   and is encoded as followed
                      - 0000: LED is not present
                      - 0001: LED is off
                      - 0010: LED is on 
                      
                   NOTE: The data is read from left to right, starting out with blade 
                   server 1 and so on."   
                   ::= { smLEDsEntry 2 }

     -- ********************************************************************************
     -- Blower LEDs
     -- ********************************************************************************
     blowerLEDs OBJECT IDENTIFIER ::= { leds 5 }

      blowerLEDsTable OBJECT-TYPE
                    SYNTAX  SEQUENCE OF BlowerLEDsEntry
                    MAX-ACCESS  not-accessible
                    STATUS  current -- was mandatory
                    DESCRIPTION
                    "Table of blower LEDs information.

                    NOTE: Blowers are also referred to as Chassis Cooling Devices."
                    ::= { blowerLEDs 1 }

       blowerLEDsEntry OBJECT-TYPE
                     SYNTAX BlowerLEDsEntry
                     MAX-ACCESS  not-accessible
                     STATUS  current -- was mandatory
                     DESCRIPTION
                     "Blower LEDs information entry"
                     INDEX { ledBlowerIndex }
                     ::= { blowerLEDsTable 1 }


       BlowerLEDsEntry ::= SEQUENCE {
                   ledBlowerIndex INTEGER,
                   ledBlowerId INTEGER,
                   ledBlowerExists INTEGER,
                   ledBlowerError INTEGER  
                   }

       ledBlowerIndex OBJECT-TYPE
                   SYNTAX  INTEGER (0..128)
                   MAX-ACCESS  read-only
                   STATUS  current -- was mandatory
                   DESCRIPTION
                   "Blower LEDs table index.  "
                   ::= { blowerLEDsEntry 1 }
                   
       ledBlowerId OBJECT-TYPE
                   SYNTAX  INTEGER {
                     blower1(1),
                     blower2(2),
                     blower3(3),
                     blower4(4)
                   }
                   MAX-ACCESS  read-only
                   STATUS  current -- was mandatory
                   DESCRIPTION
                   "The numeric blade ID."
                   ::= { blowerLEDsEntry 2 }

       ledBlowerExists OBJECT-TYPE
                   SYNTAX  INTEGER {
                     false(0),
                     true(1)
                   }
                   MAX-ACCESS  read-only
                   STATUS  current -- was mandatory
                   DESCRIPTION
                   "Indicates whether the blower specified exists or not."
                   ::= { blowerLEDsEntry 3 }

       ledBlowerError OBJECT-TYPE
                   SYNTAX  INTEGER {
                     off(0),
                     on(1),
                     notAvailable(2)
                   }
                   MAX-ACCESS  read-only
                   STATUS  current -- was mandatory
                   DESCRIPTION
                   "Indicates whether the blower error LED is on, off, or not available."   
                   ::= { blowerLEDsEntry 4 }

     -- ********************************************************************************
     -- Fan Pack LEDs
     -- ********************************************************************************
     fanPackLEDs OBJECT IDENTIFIER ::= { leds 6 }

      fanPackLEDsTable OBJECT-TYPE
                    SYNTAX  SEQUENCE OF FanPackLEDsEntry
                    MAX-ACCESS  not-accessible
                    STATUS  current -- was mandatory
                    DESCRIPTION
                    "Table of fan pack LEDs information.

                    NOTE: Fan packs are also referred to as Power Module Cooling Devices."
                    ::= { fanPackLEDs 1 }

       fanPackLEDsEntry OBJECT-TYPE
                     SYNTAX FanPackLEDsEntry
                     MAX-ACCESS  not-accessible
                     STATUS  current -- was mandatory
                     DESCRIPTION
                     "Fan Pack LEDs information entry"
                     INDEX { ledFanPackIndex }
                     ::= { fanPackLEDsTable 1 }


       FanPackLEDsEntry ::= SEQUENCE {
                   ledFanPackIndex INTEGER,
                   ledFanPackId INTEGER, 
                   ledFanPackExists INTEGER, 
                   ledFanPackError INTEGER  
                   }


       ledFanPackIndex OBJECT-TYPE
                   SYNTAX  INTEGER (0..128)
                   MAX-ACCESS  read-only
                   STATUS  current -- was mandatory
                   DESCRIPTION
                   "Fan Pack LEDs table index.  "
                   ::= { fanPackLEDsEntry 1 }

       ledFanPackId OBJECT-TYPE
                   SYNTAX  INTEGER {
                      fanPack1(1),
                      fanPack2(2),
                      fanPack3(3),
                      fanPack4(4)
                   }
                   MAX-ACCESS  read-only
                   STATUS  current -- was mandatory
                   DESCRIPTION
                   "The numeric fan pack ID."
                   ::= { fanPackLEDsEntry 2 }

       ledFanPackExists OBJECT-TYPE
                   SYNTAX  INTEGER (0..128)
                   MAX-ACCESS  read-only
                   STATUS  current -- was mandatory
                   DESCRIPTION
                   "Indicates whether the fan pack specified exists or not."
                   ::= { fanPackLEDsEntry 3 }
       
       ledFanPackError OBJECT-TYPE
                   SYNTAX  INTEGER (0..128)
                   MAX-ACCESS  read-only
                   STATUS  current -- was mandatory
                   DESCRIPTION
                   "Indicates whether the fan pack error LED is on or off."
                   ::= { fanPackLEDsEntry 4 }

     -- ********************************************************************************
     -- BCHT ONLY - Hardware Component Status LEDs
     -- ********************************************************************************
     -- Media Tray Status LEDs
     -- ********************************************************************************
     mtStatusLEDs OBJECT IDENTIFIER ::= { leds 7 }

        mtStatusLEDsTable OBJECT-TYPE
                   SYNTAX  SEQUENCE OF MtStatusLEDsEntry
                   MAX-ACCESS  not-accessible
                   STATUS  current -- was mandatory
                   DESCRIPTION
                   "Table of Media Tray Status LEDs information.
                    
                   NOTE: This MIB object is for BladeCenter HT only."
                   ::= { mtStatusLEDs 1 }

        mtStatusLEDsEntry OBJECT-TYPE
                   SYNTAX MtStatusLEDsEntry
                   MAX-ACCESS  not-accessible
                   STATUS  current -- was mandatory
                   DESCRIPTION
                   "Media Tray Status LEDs information entry.
                     
                   NOTE: This MIB object is for BladeCenter HT only."
                   INDEX { ledMediaTrayIndex }
                   ::= { mtStatusLEDsTable 1 }


        MtStatusLEDsEntry ::= SEQUENCE {
                   ledMediaTrayIndex INTEGER,
                   ledMediaTrayId INTEGER, 
                   ledMediaTrayExists INTEGER, 
                   ledMediaTrayFault INTEGER  
                   }


        ledMediaTrayIndex OBJECT-TYPE
                   SYNTAX  INTEGER (0..128)
                   MAX-ACCESS  read-only
                   STATUS  current -- was mandatory
                   DESCRIPTION
                   "Media Tray Status LEDs table index.  
                   
                   NOTE: This MIB object is for BladeCenter HT only."
                   ::= { mtStatusLEDsEntry 1 }


        ledMediaTrayId OBJECT-TYPE
                   SYNTAX  INTEGER {
                     topmediatray(1),
                     botmediatray(2)
                   }
                   MAX-ACCESS  read-only
                   STATUS  current -- was mandatory
                   DESCRIPTION
                   "The numeric Media Tray ID.
                   
                   NOTE: This MIB object is for BladeCenter HT only."
                   ::= { mtStatusLEDsEntry 2 }
       
        ledMediaTrayExists OBJECT-TYPE
                   SYNTAX  INTEGER {
                      false(0),
                      true(1)
                   }
                   MAX-ACCESS  read-only
                   STATUS  current -- was mandatory
                   DESCRIPTION
                   "Indicates whether the Media Tray exists or not.
                   
                   NOTE: This MIB object is for BladeCenter HT only."
                   ::= { mtStatusLEDsEntry 3 }
                   
        ledMediaTrayFault OBJECT-TYPE
                   SYNTAX  INTEGER {
                      off(0),
                      on(1)
                   }
                   MAX-ACCESS  read-only
                   STATUS  current -- was mandatory
                   DESCRIPTION
                   "Indicates whether the Media Tray Fault LED is on or off.
                   
                   NOTE: This MIB object is for BladeCenter HT only."
                   ::= { mtStatusLEDsEntry 5 }
                   
     -- ********************************************************************************
     -- Telco Alarm Panel Tray Status LEDs
     -- ********************************************************************************
     tapStatusLEDs OBJECT IDENTIFIER ::= { leds 8 }

        tapExists  OBJECT-TYPE
                   SYNTAX INTEGER {
                     false(0),
                     true(1)
                   }
                   MAX-ACCESS  read-only
                   STATUS  current -- was mandatory
                   DESCRIPTION
                   "Indicates whether the Alarm Panel exists or not.
                   
                   NOTE: This MIB object is for BladeCenter HT only."
                   ::= { tapStatusLEDs 3 }

        tapFRRLED  OBJECT-TYPE
                   SYNTAX INTEGER {
                     off(0),
                     on(1)
                   }
                   MAX-ACCESS  read-only
                   STATUS  current -- was mandatory
                   DESCRIPTION
                   "Indicates whether the Alarm Panel Safe To Remove LED is on or off.
                   
                   NOTE: This MIB object is for BladeCenter HT only."
                   ::= { tapStatusLEDs 4 }


        tapFaultLED OBJECT-TYPE
                   SYNTAX INTEGER {
                     off(0),
                     on(1)
                   }
                   MAX-ACCESS  read-only
                   STATUS  current -- was mandatory
                   DESCRIPTION
                   "Indicates whether the Alarm Panel Fault LED is on or off.
                   
                   NOTE: This MIB object is for BladeCenter HT only."
                   ::= { tapStatusLEDs 5 }
                   

     -- ********************************************************************************
     -- Network Clock Status LEDs
     -- ********************************************************************************
     ncStatusLEDs OBJECT IDENTIFIER ::= { leds 9 }

        ncStatusLEDsTable OBJECT-TYPE
                   SYNTAX  SEQUENCE OF NcStatusLEDsEntry
                   MAX-ACCESS  not-accessible
                   STATUS  current -- was mandatory
                   DESCRIPTION
                   "Table of Network Clock Status LEDs information.
                    
                   NOTE: This MIB object is for BladeCenter HT only."
                   ::= { ncStatusLEDs 1 }

        ncStatusLEDsEntry OBJECT-TYPE
                   SYNTAX NcStatusLEDsEntry
                   MAX-ACCESS  not-accessible
                   STATUS  current -- was mandatory
                   DESCRIPTION
                   "Network Clock Status LEDs information entry.
                     
                   NOTE: This MIB object is for BladeCenter HT only."
                   INDEX { ledNetworkClockIndex }
                   ::= { ncStatusLEDsTable 1 }


        NcStatusLEDsEntry ::= SEQUENCE {
                   ledNetworkClockIndex INTEGER,
                   ledNetworkClockId INTEGER, 
                   ledNetworkClockExists INTEGER, 
                   ledNetworkClockFRR INTEGER,  
                   ledNetworkClockFault INTEGER  
                   }


        ledNetworkClockIndex OBJECT-TYPE
                   SYNTAX  INTEGER (0..128)
                   MAX-ACCESS  read-only
                   STATUS  current -- was mandatory
                   DESCRIPTION
                   "Network Clock Status LEDs table index.  
                   
                   NOTE: This MIB object is for BladeCenter HT only."
                   ::= { ncStatusLEDsEntry 1 }


        ledNetworkClockId OBJECT-TYPE
                   SYNTAX  INTEGER {
                     networkclock1(1),
                     networkclock2(2)
                   }
                   MAX-ACCESS  read-only
                   STATUS  current -- was mandatory
                   DESCRIPTION
                   "The numeric Network Clock ID.
                   
                   NOTE: This MIB object is for BladeCenter HT only."
                   ::= { ncStatusLEDsEntry 2 }
       
        ledNetworkClockExists OBJECT-TYPE
                   SYNTAX INTEGER {
                     false(0),
                     true(1)
                   }
                   MAX-ACCESS  read-only
                   STATUS  current -- was mandatory
                   DESCRIPTION
                   "Indicates whether the Network Clock exists or not.
                   
                   NOTE: This MIB object is for BladeCenter HT only."
                   ::= { ncStatusLEDsEntry 3 }
       
        ledNetworkClockFRR OBJECT-TYPE
                   SYNTAX  INTEGER {
                      off(0),
                      on(1)
                   }
                   MAX-ACCESS  read-only
                   STATUS  current -- was mandatory
                   DESCRIPTION
                   "Indicates whether the Network Clock Safe To Remove LED is on or off.
                   
                   NOTE: This MIB object is for BladeCenter HT only."
                   ::= { ncStatusLEDsEntry 4 }
       
        ledNetworkClockFault OBJECT-TYPE
                   SYNTAX  INTEGER {
                      off(0),
                      on(1)
                   }
                   MAX-ACCESS  read-only
                   STATUS  current -- was mandatory
                   DESCRIPTION
                   "Indicates whether the Network Clock Fault LED is on or off.
                   
                   NOTE: This MIB object is for BladeCenter HT only."
                   ::= { ncStatusLEDsEntry 5 }
                   

     -- ********************************************************************************
     -- Multiplexer Expansion Module Status LEDs
     -- ********************************************************************************
     mxStatusLEDs OBJECT IDENTIFIER ::= { leds 10 }

        mxStatusLEDsTable OBJECT-TYPE
                   SYNTAX  SEQUENCE OF MxStatusLEDsEntry
                   MAX-ACCESS  not-accessible
                   STATUS  current -- was mandatory
                   DESCRIPTION
                   "Table of Multiplexer Expansion Module Status LEDs information.
                    
                   NOTE: This MIB object is for BladeCenter HT only."
                   ::= { mxStatusLEDs 1 }

        mxStatusLEDsEntry OBJECT-TYPE
                   SYNTAX MxStatusLEDsEntry
                   MAX-ACCESS  not-accessible
                   STATUS  current -- was mandatory
                   DESCRIPTION
                   "Multiplexer Expansion Module Status LEDs information entry.
                     
                   NOTE: This MIB object is for BladeCenter HT only."
                   INDEX { ledMuxIndex }
                   ::= { mxStatusLEDsTable 1 }


        MxStatusLEDsEntry ::= SEQUENCE {
                   ledMuxIndex INTEGER,
                   ledMuxId INTEGER, 
                   ledMuxExists INTEGER, 
                   ledMuxFRR INTEGER,  
                   ledMuxFault INTEGER  
                   }


        ledMuxIndex OBJECT-TYPE
                   SYNTAX  INTEGER (0..128)
                   MAX-ACCESS  read-only
                   STATUS  current -- was mandatory
                   DESCRIPTION
                   "Multiplexer Expansion Module Status LEDs table index.  
                   
                   NOTE: This MIB object is for BladeCenter HT only."
                   ::= { mxStatusLEDsEntry 1 }


        ledMuxId   OBJECT-TYPE
                   SYNTAX  INTEGER {
                     mux1(1),
                     mux2(2)
                   }
                   MAX-ACCESS  read-only
                   STATUS  current -- was mandatory
                   DESCRIPTION
                   "The numeric Multiplexer Expansion Module ID.
                   
                   NOTE: This MIB object is for BladeCenter HT only."
                   ::= { mxStatusLEDsEntry 2 }
       
        ledMuxExists OBJECT-TYPE
                   SYNTAX INTEGER {
                     false(0),
                     true(1)
                   }
                   MAX-ACCESS  read-only
                   STATUS  current -- was mandatory
                   DESCRIPTION
                   "Indicates whether the Multiplexer Expansion Module exists or not.
                   
                   NOTE: This MIB object is for BladeCenter HT only."
                   ::= { mxStatusLEDsEntry 3 }
       
        ledMuxFRR  OBJECT-TYPE
                   SYNTAX  INTEGER {
                      off(0),
                      on(1)
                   }
                   MAX-ACCESS  read-only
                   STATUS  current -- was mandatory
                   DESCRIPTION
                   "Indicates whether the Multiplexer Expansion Module Safe To Remove LED is on or off.
                   
                   NOTE: This MIB object is for BladeCenter HT only."
                   ::= { mxStatusLEDsEntry 4 }
       
        ledMuxFault OBJECT-TYPE
                   SYNTAX  INTEGER {
                      off(0),
                      on(1)
                   }
                   MAX-ACCESS  read-only
                   STATUS  current -- was mandatory
                   DESCRIPTION
                   "Indicates whether the Multiplexer Expansion Module Fault LED is on or off.
                   
                   NOTE: This MIB object is for BladeCenter HT only."
                   ::= { mxStatusLEDsEntry 5 }
                   

     -- ********************************************************************************
     -- Storage LEDs
     -- ********************************************************************************
     storageLEDs OBJECT IDENTIFIER ::= { leds 11 }

      storageLEDsTable OBJECT-TYPE
                    SYNTAX  SEQUENCE OF StorageLEDsEntry
                    MAX-ACCESS  not-accessible
                    STATUS  current -- was mandatory
                    DESCRIPTION
                    "Table of storage module LEDs information."
                    ::= { storageLEDs 1 }

       storageLEDsEntry OBJECT-TYPE
                     SYNTAX StorageLEDsEntry
                     MAX-ACCESS  not-accessible
                     STATUS  current -- was mandatory
                     DESCRIPTION
                     "Storage Module LEDs information entry"
                     INDEX { ledStorageIndex }
                     ::= { storageLEDsTable 1 }


       StorageLEDsEntry ::= SEQUENCE {
                   ledStorageIndex INTEGER,
                   ledStorageId INTEGER, 
                   ledStorageExists INTEGER, 
                   ledStorageError INTEGER  
                   }


       ledStorageIndex OBJECT-TYPE
                   SYNTAX  Integer32 (0..2147483647) -- was INTEGER
                   MAX-ACCESS  read-only
                   STATUS  current -- was mandatory
                   DESCRIPTION
                   "Storage Module LEDs table index."
                   ::= { storageLEDsEntry 1 }

       ledStorageId OBJECT-TYPE
                   SYNTAX  INTEGER {
                      storage1(1),
                      storage2(2)
                   }
                   MAX-ACCESS  read-only
                   STATUS  current -- was mandatory
                   DESCRIPTION
                   "The numeric storage module ID."
                   ::= { storageLEDsEntry 2 }

       ledStorageExists OBJECT-TYPE
                   SYNTAX  INTEGER {
                      false(0),
                      true(1)
                   }
                   MAX-ACCESS  read-only
                   STATUS  current -- was mandatory
                   DESCRIPTION
                   "Indicates whether the storage module specified exists or not."
                   ::= { storageLEDsEntry 3 }
       
       ledStorageError OBJECT-TYPE
                   SYNTAX  INTEGER {
                     off(0),
                     on(1),
                     blinking(2)
                   }
                   MAX-ACCESS  read-only
                   STATUS  current -- was mandatory
                   DESCRIPTION
                   "Indicates the status of the storage module error LED."
                   ::= { storageLEDsEntry 4 }

     -- ************************************************************************
     -- BladeCenter T System Health
     -- ************************************************************************
     telcoSystemHealth OBJECT IDENTIFIER ::= { monitors 9 }

     -- ************************************************************************
     -- BladeCenter T System Health Status
     -- ************************************************************************
     telcoSystemHealthStat  OBJECT-TYPE
                   SYNTAX  INTEGER {
                                     critical-power(6),
                                     critical(5),
                                     major-power(4),
                                     major(3),
                                     minor-power(2),
                                     minor(1),
                                     normal(255)
                                   }
                   MAX-ACCESS  read-only
                   STATUS  current -- was mandatory
                   DESCRIPTION
                   "Indicates status of system health for the system in which the 
                   MM resides. Value of 'critical' indicates a non-recoverable 
                   service affecting condition has occurred that requires an 
                   immediate action. A value of 'major' indicates a critical 
                   service affecting condition has occurred that requires an urgent
                   action. A value of 'minor' indicates a non-service affecting 
                   condition has occurred. Corrective action should be taken in 
                   order to prevent a more serious fault. A value of 'normal' 
                   indicates that the system is operating normally. Severity level
                   with '-power' indicates the failure relates to the power resource.
                   
                   NOTE: This MIB object is for BladeCenter T only." 
                   ::= { telcoSystemHealth 1 }

     -- ************************************************************************
     -- BladeCenter T System Health Summary
     -- ************************************************************************
     telcoSystemHealthSummaryTable OBJECT-TYPE
                   SYNTAX  SEQUENCE OF TelcoSystemHealthSummaryEntry
                   MAX-ACCESS  not-accessible
                   STATUS  current -- was mandatory
                   DESCRIPTION
                   "Table of System Health summary. Contains more detailed
                   information about the reasons for the overall system
                   health status.
                   
                   NOTE: This MIB object is for BladeCenter T only.
                   NOTE: This table may contain one entry if no alarms are in progress.  That one entry,
                        if present, contains no alarms but a message of 'Good' in the severity object." 
                   ::= { telcoSystemHealth 2 }

     telcoSystemHealthSummaryEntry OBJECT-TYPE
                   SYNTAX TelcoSystemHealthSummaryEntry
                   MAX-ACCESS  not-accessible
                   STATUS  current -- was mandatory
                   DESCRIPTION
                   "BladeCenter T System Health Summary entry.
                   
                   NOTE: This MIB object is for BladeCenter T only." 
                   INDEX { telcoSystemHealthSummaryIndex }
                   ::= { telcoSystemHealthSummaryTable 1 }


     TelcoSystemHealthSummaryEntry ::= SEQUENCE {
                   telcoSystemHealthSummaryIndex INTEGER,
                   telcoSystemHealthSummarySeverity OCTET STRING,
                   telcoSystemHealthSummaryDescription OCTET STRING,
                   telcoSystemHealthSummaryEventName INTEGER,
                   telcoSystemHealthSummaryEventKeyID OCTET STRING,
                   telcoSystemHealthSummaryAcknowledge INTEGER,
                   telcoSystemHealthSummaryAssertTime OCTET STRING
                   }


     telcoSystemHealthSummaryIndex  OBJECT-TYPE
                   SYNTAX  Integer32 (0..2147483647) -- was INTEGER
                   MAX-ACCESS  read-only
                   STATUS  current -- was mandatory
                   DESCRIPTION
                   "BladeCenter T System Health Summary Index.
                   
                   NOTE: This MIB object is for BladeCenter T only." 
                   ::= { telcoSystemHealthSummaryEntry 1 }

     telcoSystemHealthSummarySeverity  OBJECT-TYPE
                   SYNTAX  OCTET STRING
                   MAX-ACCESS  read-only
                   STATUS  current -- was mandatory
                   DESCRIPTION
                   "BladeCenter T System Health Summary Severity. The values 
                   and meanings are as follows:
                      0x06 Critical-Power
                      0x05 Critical 
                      0x04 Major-Power
                      0x03 Major 
                      0x02 Minor-Power
                      0x01 Minor 
                      0xFF Normal
                      
                   NOTE: This MIB object is for BladeCenter T only.
                   NOTE: If no alarms are in progress, this object contains 'Good'." 
                   ::= { telcoSystemHealthSummaryEntry 2 }

     telcoSystemHealthSummaryDescription  OBJECT-TYPE
                   SYNTAX  OCTET STRING
                   MAX-ACCESS  read-only
                   STATUS  current -- was mandatory
                   DESCRIPTION
                   "BladeCenter T System Health Summary Description.
                   
                   NOTE: This MIB object is for BladeCenter T only.
                   NOTE: If no alarms are in progress, this object contains 'No alarm events'." 
                   ::= { telcoSystemHealthSummaryEntry 3 }
                 
     telcoSystemHealthSummaryEventName  OBJECT-TYPE
                   SYNTAX INTEGER 
                   MAX-ACCESS  read-only
                   STATUS  current -- was mandatory
                   DESCRIPTION
                   "BladeCenter T System Health Summary Event Name.
                   
                   NOTE: This MIB object is for BladeCenter T only." 
                   ::= { telcoSystemHealthSummaryEntry 4 }
       
     telcoSystemHealthSummaryEventKeyID  OBJECT-TYPE
                   SYNTAX OCTET STRING 
                   MAX-ACCESS  read-only
                   STATUS  current -- was mandatory
                   DESCRIPTION
                   "BladeCenter T System Health Summary Event Key ID. An octet string 
                   expressed as 'mmm:ggg:iii:aaa:sss' where: 
                      m : Module ID value of decimal digits(1-255) or 
                          blank space(s) for leading zero(s)
                      g : Gen ID value of decimal digits(1-255) or 
                          blank space(s) for leading zero(s)
                      i : GenInfo ID value of decimal digits(1-255) or
                          blank space(s) for leading zero(s)
                      a : Alarm ID value of decimal digits(1-255) or
                          blank space(s) for leading zero(s) 
                      s : Alarm severity value of decimal digits(1-255) or
                          blank space(s) for leading zero(s) 

                           
                   NOTE: This MIB object is for BladeCenter T only.
                   NOTE: If no alarms are in progress, this object contains 'No alarm events'." 
                   ::= { telcoSystemHealthSummaryEntry 5 }
     
     telcoSystemHealthSummaryAcknowledge  OBJECT-TYPE
                   SYNTAX INTEGER {
                     unacknowledged(0),
                     acknowledged(1)
                   }
                   MAX-ACCESS  read-only
                   STATUS  current -- was mandatory
                   DESCRIPTION
                   "BladeCenter T System Health Summary Acknowledge. Indicates whether the
                   alarm event is acknowledged or unacknowledged.
                   
                   NOTE: This MIB object is for BladeCenter T only." 
                   ::= { telcoSystemHealthSummaryEntry 6 }
    
     telcoSystemHealthSummaryAssertTime  OBJECT-TYPE
                   SYNTAX  OCTET STRING
                   MAX-ACCESS  read-only
                   STATUS  current -- was mandatory
                   DESCRIPTION
                   "BladeCenter T System Health Summary Assert Time.
                   
                   NOTE: This MIB object is for BladeCenter T only.
                   NOTE: If no alarms are in progress, this object contains 'No alarm events'." 
                   ::= { telcoSystemHealthSummaryEntry 7 }
                         
      


    -- ********************************************************************************
    -- Fuel Gauge / Power Management 
    -- ********************************************************************************
    fuelGauge OBJECT IDENTIFIER ::= { monitors 10 }

     -- ********************************************************************************
     -- Fuel Gauge
     -- ********************************************************************************
     fuelGaugeInformation  OBJECT IDENTIFIER ::= { fuelGauge 1 }
     
      fuelGaugeTable OBJECT-TYPE
                   SYNTAX  SEQUENCE OF FuelGaugeEntry
                   MAX-ACCESS  not-accessible
                   STATUS  current -- was mandatory
                   DESCRIPTION
                   "Table of Fuel Gauge information."
                   ::= { fuelGaugeInformation 1 }

      fuelGaugeEntry OBJECT-TYPE
                   SYNTAX FuelGaugeEntry
                   MAX-ACCESS  not-accessible
                   STATUS  current -- was mandatory
                   DESCRIPTION
                   "Fuel Gauge entry"
                   INDEX { fuelGaugeIndex }
                   ::= { fuelGaugeTable 1 }

      FuelGaugeEntry ::= SEQUENCE {
                 fuelGaugeIndex INTEGER,
                 fuelGaugePowerDomainNumber INTEGER,
                 fuelGaugeStatus OCTET STRING,
                 fuelGaugeFirstPowerModule OCTET STRING,
                 fuelGaugeSecondPowerModule OCTET STRING,
                 fuelGaugePowerManagementPolicySetting INTEGER,
                 fuelGaugeTotalPower OCTET STRING,
                 fuelGaugeAllocatedPower OCTET STRING,
                 fuelGaugeRemainingPower OCTET STRING,
                 fuelGaugePowerInUsed OCTET STRING
                 }

      fuelGaugeIndex  OBJECT-TYPE
                 SYNTAX  Integer32 (0..2147483647) -- was INTEGER
                 MAX-ACCESS  read-only
                 STATUS  current -- was mandatory
                 DESCRIPTION
                 "Fuel Gauge Table Index."
                 ::= { fuelGaugeEntry 1 }

      fuelGaugePowerDomainNumber  OBJECT-TYPE
                 SYNTAX  INTEGER {
                   powerDomain1(1), 
                   powerDomain2(2)       
                 }
                 MAX-ACCESS  read-only
                 STATUS  current -- was mandatory
                 DESCRIPTION
                 "Fuel Gauge Table Power Domain Number."
                 ::= { fuelGaugeEntry 2 }
                 
      fuelGaugeStatus  OBJECT-TYPE
                 SYNTAX  OCTET STRING
                 MAX-ACCESS  read-only
                 STATUS  current -- was mandatory
                 DESCRIPTION
                 "Fuel Gauge Table Status for the power domain.  
                 The response will start out with a numeric value (0 = unknown, 
                 1 = good, 2 = warning, and 3: bad), followed by a text message."
                 ::= { fuelGaugeEntry 3 }

      fuelGaugeFirstPowerModule  OBJECT-TYPE
                 SYNTAX  OCTET STRING
                 MAX-ACCESS  read-only
                 STATUS  current -- was mandatory
                 DESCRIPTION
                 "Fuel Gauge Table First Power Module capacity in Watts in the power domain.  
                 
                 NOTE: First power module in power domain 1 and 2 is in bay 1 
                 and 3 respectively."
                 ::= { fuelGaugeEntry 4 }

      fuelGaugeSecondPowerModule  OBJECT-TYPE
                 SYNTAX  OCTET STRING
                 MAX-ACCESS  read-only
                 STATUS  current -- was mandatory
                 DESCRIPTION
                 "Fuel Gauge Table Second Power Module capacity in Watts in the power domain.
                 
                 NOTE: Second power module in power domain 1 and 2 is in bay 2 
                 and 4 respectively."
                 ::= { fuelGaugeEntry 5 }

      fuelGaugePowerManagementPolicySetting  OBJECT-TYPE
                 SYNTAX  INTEGER {
                   redundantWithoutPerformanceImpact(0),
                   redundantWithPerformanceImpact(1), 
                   nonRedundant(2),
                   redundantACPowerSource(3),   
                   acPowerSourceWithBladeThrottlingAllowed(4), 
                   notApplicable(255)
                 }
                 MAX-ACCESS  read-only
                 STATUS  current -- was mandatory
                 DESCRIPTION
                 "Fuel Gauge Table for the Power Management Policy Setting for each power domain.
                 When a 1200W or 1400W power module is installed in the domain 
                 the power management policy will not be applicable. 
                 In addition the power consumption in this domain will not be monitored.
                 
                 A new powerPolicyTable has been added which provides more detailed 
                 information regarding a domains power policy information. This table 
                 also has the capability to SET the power policy for a given domain.
                 
                 In addition, note that the first three enumerated choices above are 
                 referred to with updated nomenclature, as follows:
                 
                   redundantWithoutPerformanceImpact(0) equals Redundant Power Modules 
                   redundantWithPerformanceImpact(1) equals Power Modules with Blade
                                                            Throttling Allowed  
                   nonRedundant(2) equals Basic Power Management"
                 ::= { fuelGaugeEntry 6 }
       
       fuelGaugeTotalPower  OBJECT-TYPE
                 SYNTAX  OCTET STRING
                 MAX-ACCESS  read-only
                 STATUS  current -- was mandatory
                 DESCRIPTION
                 "This field displays the total available power for each power domain based on 
                 installed power modules and the current Power Management Policy Setting.                 
                 When a 1200W or 1400W power module is installed in the domain 
                 the power management policy will not be applicable. 
                 In addition the power consumption in this domain will not be monitored."
                 ::= { fuelGaugeEntry 7 }          

      fuelGaugeAllocatedPower  OBJECT-TYPE
                 SYNTAX  OCTET STRING
                 MAX-ACCESS  read-only
                 STATUS  current -- was mandatory
                 DESCRIPTION
                 "This field displays the power that has been reserved in each power domain.                   
                 NOTE: 1) Power is always reserved in domain 1 for two management modules and 
                 two I/O modules.  2) Power is reserved for I/O modules installed in bay 3 and 
                 4  (Powered on or standby). 3) Power is reserved for each installed Blade. 
                 Blades in a standby state (not powered on) will reserve a certain amount power.
                 When a 1200W or 1400W power module is installed in the domain 
                 the power management policy will not be applicable. 
                 In addition the power consumption in this domain will not be monitored."
                 ::= { fuelGaugeEntry 8 }          

      fuelGaugeRemainingPower  OBJECT-TYPE
                 SYNTAX  OCTET STRING
                 MAX-ACCESS  read-only
                 STATUS  current -- was mandatory
                 DESCRIPTION
                 "This field displays the remaining power available in each domain. 
                 Remaining Power = Total Power minus Power In Use 
                 When a 1200W or 1400W power module is installed in the domain 
                 the power management policy will not be applicable. 
                 In addition the power consumption in this domain will not be monitored."
                 ::= { fuelGaugeEntry 9 }
     
      fuelGaugePowerInUsed  OBJECT-TYPE
                 SYNTAX  OCTET STRING
                 MAX-ACCESS  read-only
                 STATUS  current -- was mandatory
                 DESCRIPTION
                 "This field displays the total power being used in each power domain.
                 When a 1200W or 1400W power module is installed in the domain 
                 the power management policy will not be applicable. 
                 In addition the power consumption in this domain will not be monitored."
                 ::= { fuelGaugeEntry 10 }          

     -- ********************************************************************************
     -- Fuel Gauge Power Domain 1
     -- ********************************************************************************
     powerDomain1  OBJECT IDENTIFIER ::= { fuelGauge 2 }
             
      powerDomain1Table OBJECT-TYPE
                   SYNTAX  SEQUENCE OF PowerDomain1Entry
                   MAX-ACCESS  not-accessible
                   STATUS  current -- was mandatory
                   DESCRIPTION
                   "Table of Power Domain 1.
           
                   NOTE: Blowers are also referred to as Chassis Cooling Devices.
                   NOTE: Fan packs are also referred to as Power Module Cooling Devices."
                   ::= { powerDomain1 1}

      powerDomain1Entry OBJECT-TYPE
                   SYNTAX PowerDomain1Entry
                   MAX-ACCESS  not-accessible
                   STATUS  current -- was mandatory
                   DESCRIPTION
                   "Fuel Gauge entry"
                   INDEX { pd1Index }
                   ::= { powerDomain1Table 1 }


      PowerDomain1Entry ::= SEQUENCE {
                 pd1Index INTEGER,
                 pd1BayNumber OCTET STRING,
                 pd1BladePrimarySlot INTEGER, 
                 pd1ModuleStatus INTEGER,
                 pd1ModuleName OCTET STRING,
                 pd1ModuleState INTEGER,
                 pd1ModuleAllocatedPowerCurrent OCTET STRING,
                 pd1ModuleAllocatedPowerMax OCTET STRING,
                 pd1ModuleAllocatedPowerMin OCTET STRING,
                 pd1ModuleCPUDutyCycles OCTET STRING,
                 pd1ModuleThrottle INTEGER,
                 pd1ModulePowerCapabilities INTEGER,
                 pd1ModuleMeasuredOrStatic INTEGER
                 }
 
      pd1Index  OBJECT-TYPE
                 SYNTAX  Integer32 (0..2147483647) -- was INTEGER
                 MAX-ACCESS  read-only
                 STATUS  current -- was mandatory
                 DESCRIPTION
                 "Power Domain 1 Table Index."
                 ::= { powerDomain1Entry 1 }

      pd1BayNumber  OBJECT-TYPE
                 SYNTAX  OCTET STRING
                 MAX-ACCESS  read-only
                 STATUS  current -- was mandatory
                 DESCRIPTION
                 "Power Domain 1 Table Bay Number.
                  The following Bay Number IDs are used in the BladeCenter:
                   notApplicable(1), 
                   notApplicable(2), 
                   blowerBay1(3), 
                   blowerBay2(4), 
                   managementModuleBay1(5), 
                   managementModuleBay2(6),
                   switchModuleBay1(7), 
                   switchModuleBay2(8),
                   switchModuleBay3(9),
                   switchModuleBay4(10),
                   serverBladeBay1(11),  
                   serverBladeBay2(12),  
                   serverBladeBay3(13),  
                   serverBladeBay4(14),  
                   serverBladeBay5(15),  
                   serverBladeBay6(16),
                   notApplicable(17)
                  The following Bay Number IDs are used in the BladeCenter H:
                   notApplicable(1), 
                   notApplicable(2), 
                   fanPackBay1(3), 
                   fanPackBay2(4), 
                   fanPackBay3(5), 
                   fanPackBay4(6), 
                   managementModuleBay1(7), 
                   managementModuleBay2(8),
                   ioModuleBay1(9), 
                   ioModuleBay2(10),
                   ioModuleBay3(11),
                   ioModuleBay4(12),
                   ioModuleBay7(13),
                   ioModuleBay8(14),
                   ioModuleBay9(15),
                   ioModuleBay10(16),
                   serverBladeBay1(17),  
                   serverBladeBay2(18),  
                   serverBladeBay3(19),  
                   serverBladeBay4(20),  
                   serverBladeBay5(21),  
                   serverBladeBay6(22),
                   serverBladeBay7(23),
                   notApplicable(24)
                  The following Bay Number IDs are used in the BladeCenter T:
                   notApplicable(1), 
                   notApplicable(2), 
                   blowerBay1(3), 
                   blowerBay2(4), 
                   blowerBay3(5) (if Power Domain 2 is not available),
                   blowerBay4(6) (if Power Domain 2 is not available),
                   managementModuleBay1(7), 
                   managementModuleBay2(8),
                   switchModuleBay1(9), 
                   switchModuleBay2(10),
                   switchModuleBay3(11),
                   switchModuleBay4(12),
                   serverBladeBay1(13),  
                   serverBladeBay2(14),  
                   serverBladeBay3(15),  
                   serverBladeBay4(16),  
                   notApplicable(17)
                  The following Bay Number IDs are used in the BladeCenter HT:
                   notApplicable(1),       
                   mediatrayBay1(2),       
                   mediatrayBay2(3),       
                   fanPackBay1(4),         
                   fanPackBay2(5),         
                   fanPackBay3(6),         
                   fanPackBay4(7),         
                   blowerBay1(8),          
                   blowerBay2(9),          
                   blowerBay3(10),         
                   blowerBay4(11),         
                   networkclockBay1(12),   
                   networkclockBay2(13),   
                   midplaneelectroBay1(14),
                   midplaneelectroBay2(15),
                   notApplicable(16),      
                   managementModuleBay1(17),
                   managementModuleBay2(18),
                   ioModuleBay1(19),       
                   ioModuleBay2(20),       
                   ioModuleBay3(21),       
                   ioModuleBay4(22),       
                   serverBladeBay1(23),    
                   serverBladeBay2(24),    
                   serverBladeBay3(25),    
                   serverBladeBay4(26),    
                   serverBladeBay5(27),    
                   serverBladeBay6(28),    
                   notApplicable(29)                   
                  The following Bay Number IDs are used in the BladeCenter S:
                   notApplicable(1),       
                   notApplicable(2),       
                   fanPackBay1(3),       
                   fanPackBay2(4),         
                   fanPackBay3(5),         
                   fanPackBay4(6),         
                   blowerBay1(7),         
                   blowerBay2(8),          
                   blowerBay3(9),          
                   blowerBay4(10),         
                   storageModuleBay1(11),         
                   storageModuleBay2(12),   
                   managementModuleBay(13),   
                   ioModuleBay1(14),
                   ioModuleBay2(15),
                   ioModuleBay3(16),      
                   ioModuleBay4(17),
                   serverBladeBay1(18),
                   serverBladeBay2(19),       
                   serverBladeBay3(20),       
                   serverBladeBay4(21),       
                   serverBladeBay5(22),       
                   serverBladeBay6(23),    
                   notApplicable(24)"
                 ::= { powerDomain1Entry 2 }

      pd1BladePrimarySlot  OBJECT-TYPE
                 SYNTAX  INTEGER  {
                   no(0), 
                   yes(1),
                   notApplicable(255)
                 }       
                 MAX-ACCESS  read-only
                 STATUS  current -- was mandatory
                 DESCRIPTION
                 "Power Domain 1 Table Blade Primary Slot can be useful 
                 when a server blade spans multiple slots (e.g. double wide or 
                 triple wide).  For example if the blade is double wide and 
                 is installed in slot 3 and 4.  3 is primary slot while 4 is not." 
                 ::= { powerDomain1Entry 3 }

      pd1ModuleStatus  OBJECT-TYPE
                 SYNTAX  INTEGER  {
                   insufficientPower(0), 
                   moduleIsThrottling(1),
                   moduleNotThrottling(2),
                   notApplicable(255)
                 }       
                 MAX-ACCESS  read-only
                 STATUS  current -- was mandatory
                 DESCRIPTION
                 "Power Domain 1 Table Module Throttle Status."
                 ::= { powerDomain1Entry 4 }

      pd1ModuleName  OBJECT-TYPE
                 SYNTAX  OCTET STRING
                 MAX-ACCESS  read-only
                 STATUS  current -- was mandatory
                 DESCRIPTION
                 "Power Domain 1 Table Module Name."
                 ::= { powerDomain1Entry 5 }

      pd1ModuleState  OBJECT-TYPE
                 SYNTAX  INTEGER {
                   standby(0),
                   on(1),
                   notPresent(2),
                   off(3),
                   hibernate(4),
                   notApplicable(255)
                 }       
                 MAX-ACCESS  read-only
                 STATUS  current -- was mandatory
                 DESCRIPTION
                 "Power Domain 1 Table Module State."
                 ::= { powerDomain1Entry 6 }
                                                         
      pd1ModuleAllocatedPowerCurrent  OBJECT-TYPE
                 SYNTAX  OCTET STRING
                 MAX-ACCESS  read-only
                 STATUS  current -- was mandatory
                 DESCRIPTION
                 "Power Domain 1 Table Allocated Power Current indicates the current power  
                 allocation for the module in Watts. When a 1200W or 1400W power module is 
                 installed in the domain the power management policy will not be applicable. 
                 In addition the power consumption in this domain will not be monitored.
                 
                 NOTE: When a server blade spans multiple slots (e.g. double wide or 
                 triple wide), the current power allocation for the module is equally 
                 divided among the slots."
                 ::= { powerDomain1Entry 7 }

      pd1ModuleAllocatedPowerMax  OBJECT-TYPE
                 SYNTAX  OCTET STRING
                 MAX-ACCESS  read-only
                 STATUS  current -- was mandatory
                 DESCRIPTION
                 "Power Domain 1 Table Allocated Power Max indicates the maximum power 
                 allocation for the module in Watts.  It is indicative of the maximum 
                 amount of power the module will consume in the domain when it is 
                 fully populated with memory chips, expansion cards, etc. 
                 When a 1200W or 1400W power module is installed in the domain 
                 the power management policy will not be applicable. 
                 In addition the power consumption in this domain will not be monitored.
                 
                 NOTE: When a server blade spans multiple slots (e.g. double wide or 
                 triple wide), the maximum power allocation for the module is equally 
                 divided among the slots."
                 ::= { powerDomain1Entry 8 }

      pd1ModuleAllocatedPowerMin  OBJECT-TYPE
                 SYNTAX  OCTET STRING
                 MAX-ACCESS  read-only
                 STATUS  current -- was mandatory
                 DESCRIPTION
                 "Power Domain 1 Table Allocated Power Min indicates the minumum power 
                 allocation for the module in Watts.  It is indicative of the minumum 
                 power consumption of the component in the domain based on its 
                 maximum throttle limit. When a 1200W or 1400W power module is installed 
                 in the domain the power management policy will not be applicable. 
                 In addition the power consumption in this domain will not be monitored.
                 
                 NOTE: When a server blade spans multiple slots (e.g. double wide or 
                 triple wide), the minimum power allocation for the module is equally 
                 divided among the slots."
                 ::= { powerDomain1Entry 9 }
      
      pd1ModuleCPUDutyCycles  OBJECT-TYPE
                 SYNTAX  OCTET STRING
                 MAX-ACCESS  read-only
                 STATUS  current -- was mandatory
                 DESCRIPTION
                 "Power Domain 1 Table Module CPUs Duty Cycles applies to blade 
                 servers only.  It displays the duty cycle for each CPU on the blade 
                 as a percentage.  Note that some blades do not report the CPU 
                 duty cycles.  In this case, 'notApplicable' will be displayed.
                 When a 1200W or 1400W power module is installed in the domain 
                 the power management policy will not be applicable. 
                 In addition the power consumption in this domain will not be monitored.
           
                 NOTE: The CPU duty cycles are reported only on a primary slot when 
                 a server blade spans multiple slots (e.g. double wide or 
                 triple wide).  For example if the blade is double wide and 
                 is installed in slot 3 and 4.  3 is primary slot while 4 is not.
                 The CPU duty cycles are reported on slot 3 while 'notApplicable' 
                 is displayed for slot 4." 
                 ::= { powerDomain1Entry 10 }

      pd1ModuleThrottle  OBJECT-TYPE
                 SYNTAX  INTEGER  {
                   no(0), 
                   yes(1),
                   notApplicable(255)
                 }       
                 MAX-ACCESS  read-only
                 STATUS  current -- was mandatory
                 DESCRIPTION
                 "Power Domain 1 Table Module Throttle indicates whether the 
                 server blade may be allowed to throttle or not.
                 When a 1200W or 1400W power module is installed in the domain 
                 the power management policy will not be applicable. 
                 In addition the power consumption in this domain will not be monitored." 
                 ::= { powerDomain1Entry 11 }    
                 
       pd1ModulePowerCapabilities  OBJECT-TYPE
                 SYNTAX  INTEGER {
                   noAbility(0),
                   staticPowerManagement(1),
                   fixedPowerManagement(2),
                   dynamicPowerManagement(3),
                   dynamicPowerMeasurement1(4),
                   dynamicPowerMeasurement2(5),
                   dynamicPowerMeasurementWithPowerCapping(6),
                   notApplicable(255)
                 }       
                 MAX-ACCESS  read-only
                 STATUS  current -- was mandatory
                 DESCRIPTION
                 "Power Domain 1 Table Module Power Capabilities.

                 staticPowerManagement: the module with the static worst 
                     case power values.
                 fixedPowermanagement: the module with the static power values but
                     ability to throttle.
                 dynamicPowerManagement: the module with power meter capability,
                     measurement enabled, but capping disabled.
                 dynamicPowerMeasurement1: the module with power meter capability,
                     measurement enabled, phase 1 only
                 dynamicPowerMeasurement2: the module with power meter capability,
                     measurement enabled, phase 2 or higher
                 dynamicPowerMeasurementWithPowerCapping: the module with power
                     meter capability, both measurement and capping enabled, 
                     phase 2 or higher"                     
                 ::= { powerDomain1Entry 12 }

       pd1ModuleMeasuredOrStatic  OBJECT-TYPE
                 SYNTAX  INTEGER {
                   static(0),
                   measured(1),
                   notApplicable(255)
                 }       
                 MAX-ACCESS  read-only
                 STATUS  current -- was mandatory
                 DESCRIPTION
                 "Power Domain 1 Table Module Measured Or Static."
                 ::= { powerDomain1Entry 13 }   

      powerDomain1PowerTrending  OBJECT IDENTIFIER ::= { powerDomain1 3 } 

       pd1PowerTrendingPeriod  OBJECT-TYPE
                 SYNTAX  INTEGER  {
                        lastHour(0),
                        last6Hours(1),
                        last12Hours(2),
                        last24Hours(3)
                 }
                 MAX-ACCESS  read-write
                 STATUS  current -- was mandatory
                 DESCRIPTION
                 "Specify time period for power domain 1 power trending information 
                 table view.

                 NOTE: This time period should be configured before displaying the
                 following Power Trending Information table for Power Domain."
                 ::= { powerDomain1PowerTrending 1 } 

       pd1PowerTrendingSampleTable  OBJECT-TYPE
                SYNTAX  SEQUENCE OF Pd1PowerTrendingSampleEntry
                MAX-ACCESS  not-accessible
                STATUS  current -- was mandatory
                DESCRIPTION
                "Table of Power Domain 1 Power Trending Information."
                ::= { powerDomain1PowerTrending 10 }

       pd1PowerTrendingSampleEntry OBJECT-TYPE
                SYNTAX Pd1PowerTrendingSampleEntry
                MAX-ACCESS  not-accessible
                STATUS  current -- was mandatory
                DESCRIPTION
                "Power Domain 1 Power Trending Sample entry."
                INDEX { pd1PowerTrendingSampleIndex }
                ::= { pd1PowerTrendingSampleTable 1 }

       Pd1PowerTrendingSampleEntry ::= SEQUENCE {
                pd1PowerTrendingSampleIndex INTEGER,
                pd1PowerTrendingSampleTimeStamp OCTET STRING,
                pd1PowerTrendingSampleAve OCTET STRING
                }

       pd1PowerTrendingSampleIndex  OBJECT-TYPE
                SYNTAX  Integer32 (0..2147483647) -- was INTEGER
                MAX-ACCESS  read-only
                STATUS  current -- was mandatory
                DESCRIPTION
                "Power Domain 1 Power Trending Sample Table Index."
                ::= { pd1PowerTrendingSampleEntry 1 }

       pd1PowerTrendingSampleTimeStamp  OBJECT-TYPE
                SYNTAX  OCTET STRING
                MAX-ACCESS  read-only
                STATUS  current -- was mandatory
                DESCRIPTION
                "Power Domain 1 Power Trending Sample Table Timestamp."
                ::= { pd1PowerTrendingSampleEntry 2 }

       pd1PowerTrendingSampleAve  OBJECT-TYPE
                SYNTAX  OCTET STRING
                MAX-ACCESS  read-only
                STATUS  current -- was mandatory
                DESCRIPTION
                "Power Domain 1 Power Trending Table Average Power."
                ::= { pd1PowerTrendingSampleEntry 3 }                 
                 
     -- ********************************************************************************
     -- Fuel Gauge Power Domain 2
     -- ********************************************************************************
     powerDomain2  OBJECT IDENTIFIER ::= { fuelGauge 3 }

      powerDomain2Table OBJECT-TYPE
                   SYNTAX  SEQUENCE OF PowerDomain2Entry
                   MAX-ACCESS  not-accessible
                   STATUS  current -- was mandatory
                   DESCRIPTION
                   "Table of Power Domain 2.
 
                   NOTE: Blowers are also referred to as Chassis Cooling Devices.
                   NOTE: Fan packs are also referred to as Power Module Cooling Devices."
                   ::= { powerDomain2 1 }

      powerDomain2Entry OBJECT-TYPE
                   SYNTAX PowerDomain2Entry
                   MAX-ACCESS  not-accessible
                   STATUS  current -- was mandatory
                   DESCRIPTION
                   "Fuel Gauge entry"
                   INDEX { pd2Index }
                   ::= { powerDomain2Table 1 } 

      PowerDomain2Entry ::= SEQUENCE {
                 pd2Index INTEGER,
                 pd2BayNumber OCTET STRING,
                 pd2BladePrimarySlot INTEGER,
                 pd2ModuleStatus INTEGER,
                 pd2ModuleName OCTET STRING,
                 pd2ModuleState INTEGER,
                 pd2ModuleAllocatedPowerCurrent OCTET STRING,
                 pd2ModuleAllocatedPowerMax OCTET STRING,
                 pd2ModuleAllocatedPowerMin OCTET STRING,
                 pd2ModuleCPUDutyCycles OCTET STRING,
                 pd2ModuleThrottle INTEGER,
                 pd2ModulePowerCapabilities INTEGER,
                 pd2ModuleMeasuredOrStatic INTEGER                                 
                 }

      pd2Index  OBJECT-TYPE
                 SYNTAX  Integer32 (0..2147483647) -- was INTEGER
                 MAX-ACCESS  read-only
                 STATUS  current -- was mandatory
                 DESCRIPTION
                 "Power Domain 2 Table Index."
                 ::= { powerDomain2Entry 1 }

      pd2BayNumber  OBJECT-TYPE
                 SYNTAX  OCTET STRING 
                 MAX-ACCESS  read-only
                 STATUS  current -- was mandatory
                 DESCRIPTION
                 "Power Domain 2 Table Bay Number.
                  The following Bay Number IDs are used in the BladeCenter:
                   serverBladeBay7(1),  
                   serverBladeBay8(2),  
                   serverBladeBay9(3),  
                   serverBladeBay10(4), 
                   serverBladeBay11(5), 
                   serverBladeBay12(6),
                   serverBladeBay13(7), 
                   serverBladeBay14(8),
                   notApplicable(9)
                  The following Bay Number IDs are used in the BladeCenter H:
                   notApplicable(1), 
                   notApplicable(2), 
                   fanPackBay1(3), 
                   fanPackBay2(4), 
                   fanPackBay3(5), 
                   fanPackBay4(6), 
                   managementModuleBay1(7), 
                   managementModuleBay2(8),
                   ioModuleBay1(9), 
                   ioModuleBay2(10),
                   ioModuleBay3(11),
                   ioModuleBay4(12),
                   ioModuleBay7(13),
                   ioModuleBay8(14),
                   ioModuleBay9(15),
                   ioModuleBay10(16),
                   serverBladeBay1(17),  
                   serverBladeBay2(18),  
                   serverBladeBay3(19),  
                   serverBladeBay4(20),  
                   serverBladeBay5(21),  
                   serverBladeBay6(22),
                   serverBladeBay7(23),
                   notApplicable(24)
                  The following Bay Number IDs are used in the BladeCenter T:
                   blowerBay3(1), 
                   blowerBay4(2), 
                   serverBladeBay5(3),  
                   serverBladeBay6(4),  
                   serverBladeBay7(5),  
                   serverBladeBay8(6),  
                   notApplicable(7),  
                   notApplicable(8),  
                   notApplicable(9)
                  The following Bay Number IDs are used in the BladeCenter HT:
                   fanPackBay1(1),    
                   fanPackBay2(2),    
                   fanPackBay3(3),    
                   fanPackBay4(4),    
                   blowerBay1(5),     
                   blowerBay2(6),     
                   blowerBay3(7),     
                   blowerBay4(8),     
                   ioModuleBay7(9),   
                   ioModuleBay8(10),  
                   ioModuleBay9(11),  
                   ioModuleBay10(12), 
                   serverBladeBay7(13),
                   serverBladeBay8(14),
                   serverBladeBay9(15),
                   serverBladeBay10(16),
                   serverBladeBay11(17),
                   serverBladeBay12(18),
                   notApplicable(19)"  
                 ::= { powerDomain2Entry 2 }

      pd2BladePrimarySlot  OBJECT-TYPE
                 SYNTAX  INTEGER  {
                   no(0), 
                   yes(1),
                   notApplicable(255)
                 }       
                 MAX-ACCESS  read-only
                 STATUS  current -- was mandatory
                 DESCRIPTION
                 "Power Domain 2 Table Blade Primary Slot can be useful 
                 when a server blade spans multiple slots (e.g. double wide or 
                 triple wide).  For example if the blade is double wide and 
                 is installed in slot 3 and 4.  3 is primary slot while 4 is not." 
                 ::= { powerDomain2Entry 3 }

      pd2ModuleStatus  OBJECT-TYPE
                 SYNTAX  INTEGER {
                   insufficientPower(0), 
                   moduleIsThrottling(1),
                   moduleNotThrottling(2),
                   notApplicable(255)
                 }
                 MAX-ACCESS  read-only
                 STATUS  current -- was mandatory
                 DESCRIPTION
                 "Power Domain 2 Table Module throttle status."
                 ::= { powerDomain2Entry 4 }

      pd2ModuleName  OBJECT-TYPE
                 SYNTAX  OCTET STRING
                 MAX-ACCESS  read-only
                 STATUS  current -- was mandatory
                 DESCRIPTION
                 "Power Domain 2 Table Module Name."
                 ::= { powerDomain2Entry 5 }

      pd2ModuleState  OBJECT-TYPE
                 SYNTAX  INTEGER {
                   standby(0),
                   on(1),
                   notPresent(2),
                   off(3),
                   hibernate(4),
                   notApplicable(255)
                 }
                 MAX-ACCESS  read-only
                 STATUS  current -- was mandatory
                 DESCRIPTION
                 "Power Domain 2 Table Power State."
                 ::= { powerDomain2Entry 6 }
     
      pd2ModuleAllocatedPowerCurrent  OBJECT-TYPE
                 SYNTAX  OCTET STRING
                 MAX-ACCESS  read-only
                 STATUS  current -- was mandatory
                 DESCRIPTION
                 "Power Domain 2 Table Allocated Power Current indicates the current power 
                 allocation for the module. When a 1200W or 1400W power module is 
                 installed in the domain the power management policy will not be applicable. 
                 In addition the power consumption in this domain will not be monitored.
                 
                 NOTE: When a server blade spans multiple slots (e.g. double wide or 
                 triple wide), the current power allocation for the module is equally 
                 divided among the slots."
                 ::= { powerDomain2Entry 7 }

      pd2ModuleAllocatedPowerMax  OBJECT-TYPE
                 SYNTAX  OCTET STRING
                 MAX-ACCESS  read-only
                 STATUS  current -- was mandatory
                 DESCRIPTION
                 "Power Domain 2 Table Allocated Power Max indicates the maximum power 
                 allocation for the module in Watts.  It is indicative of the maximum 
                 amount of power the module will consume in the domain when it is 
                 fully populated with memory chips, expansion cards, etc.
                 When a 1200W or 1400W power module is installed in the domain 
                 the power management policy will not be applicable. In addition 
                 the power consumption in this domain will not be monitored.
                 
                 NOTE: When a server blade spans multiple slots (e.g. double wide or 
                 triple wide), the maximum power allocation for the module is equally 
                 divided among the slots."
                 ::= { powerDomain2Entry 8 }

      pd2ModuleAllocatedPowerMin  OBJECT-TYPE
                 SYNTAX  OCTET STRING
                 MAX-ACCESS  read-only
                 STATUS  current -- was mandatory
                 DESCRIPTION
                 "Power Domain 2 Table Allocated Power Min indicates the minumum power 
                 allocation for the module in Watts.  It is indicative of the minumum 
                 power consumption of the component in the domain based on its 
                 maximum throttle limit. When a 1200W or 1400W power module is 
                 installed in the domain the power management policy will not be applicable. 
                 In addition the power consumption in this domain will not be monitored.

                 NOTE: When a server blade spans multiple slots (e.g. double wide or 
                 triple wide), the minimum power allocation for the module is equally 
                 divided among the slots."
                 ::= { powerDomain2Entry 9 }

      pd2ModuleCPUDutyCycles  OBJECT-TYPE
                 SYNTAX  OCTET STRING
                 MAX-ACCESS  read-only
                 STATUS  current -- was mandatory
                 DESCRIPTION
                 "Power Domain 2 Table Module CPUs Duty Cycles applies to blade 
                 servers only.  It displays the duty cycle for each CPU on the blade 
                 as a percentage.  Note that some blades do not report the CPU 
                 duty cycles.  In this case, 'notApplicable' will be displayed.
                 When a 1200W or 1400W power module is installed in the domain 
                 the power management policy will not be applicable. 
                 In addition the power consumption in this domain will not be monitored.
                 
                 NOTE: The CPU duty cycles are reported only on a primary slot when 
                 a server blade spans multiple slots (e.g. double wide or 
                 triple wide).  For example if the blade is double wide and 
                 is installed in slot 3 and 4.  3 is primary slot while 4 is not.  
                 The CPU duty cycles are reported on slot 3 while 'notApplicable' 
                 is displayed for slot 4. " 
                 ::= { powerDomain2Entry 10 }

      pd2ModuleThrottle  OBJECT-TYPE
                 SYNTAX  INTEGER  {
                   no(0), 
                   yes(1),
                   notApplicable(255)
                 }       
                 MAX-ACCESS  read-only
                 STATUS  current -- was mandatory
                 DESCRIPTION
                 "Power Domain 2 Table Module Throttle indicates whether the 
                 server blade may be allowed to throttle or not. 
                 When a 1200W or 1400W power module is installed in the domain 
                 the power management policy will not be applicable. 
                 In addition the power consumption in this domain will not be monitored." 
                 ::= { powerDomain2Entry 11 }
                 
       pd2ModulePowerCapabilities  OBJECT-TYPE
                 SYNTAX  INTEGER {
                   noAbility(0),
                   staticPowerManagement(1),
                   fixedPowerManagement(2),
                   dynamicPowerManagement(3),
                   dynamicPowerMeasurement1(4),
                   dynamicPowerMeasurement2(5),
                   dynamicPowerMeasurementWithPowerCapping(6),
                   notApplicable(255)
                 }       
                 MAX-ACCESS  read-only
                 STATUS  current -- was mandatory
                 DESCRIPTION
                 "Power Domain 2 Table Module Power Capabilities.

                 staticPowerManagement: the module with the static worst 
                     case power values.
                 fixedPowermanagement: the module with the static power values but
                     ability to throttle.
                 dynamicPowerManagement: the module with power meter capability,
                     measurement enabled, but capping disabled.
                 dynamicPowerMeasurement1: the module with power meter capability,
                     measurement enabled, phase 1 only
                 dynamicPowerMeasurement2: the module with power meter capability,
                     measurement enabled, phase 2 or higher
                 dynamicPowerMeasurementWithPowerCapping: the module with power
                     meter capability, both measurement and capping enabled, 
                     phase 2 or higher"                                      
                 ::= { powerDomain2Entry 12 }

       pd2ModuleMeasuredOrStatic  OBJECT-TYPE
                 SYNTAX  INTEGER {
                   static(0),
                   measured(1), 
                   notApplicable(255)
                 }       
                 MAX-ACCESS  read-only
                 STATUS  current -- was mandatory
                 DESCRIPTION
                 "Power Domain 2 Table Module Measured Or Static."
                 ::= { powerDomain2Entry 13 }                 

      powerDomain2PowerTrending  OBJECT IDENTIFIER ::= { powerDomain2 3 } 

       pd2PowerTrendingPeriod  OBJECT-TYPE
                 SYNTAX  INTEGER  {
                        lastHour(0),
                        last6Hours(1),
                        last12Hours(2),
                        last24Hours(3)
                 }
                 MAX-ACCESS  read-write
                 STATUS  current -- was mandatory
                 DESCRIPTION
                 "Specify time period for power domain 2 power trending information 
                 table view.

                 NOTE: This time period should be configured before displaying the
                 following Power Trending Information table for Power Domain."                 
                 ::= { powerDomain2PowerTrending 1 } 

       pd2PowerTrendingSampleTable  OBJECT-TYPE
                SYNTAX  SEQUENCE OF Pd2PowerTrendingSampleEntry
                MAX-ACCESS  not-accessible
                STATUS  current -- was mandatory
                DESCRIPTION
                "Table of Power Domain 2 Power Trending Sample Information."
                ::= { powerDomain2PowerTrending 10 }

       pd2PowerTrendingSampleEntry OBJECT-TYPE
                SYNTAX Pd2PowerTrendingSampleEntry
                MAX-ACCESS  not-accessible
                STATUS  current -- was mandatory
                DESCRIPTION
                "Power Domain 2 Power Trending Sample entry."
                INDEX { pd2PowerTrendingSampleIndex }
                ::= { pd2PowerTrendingSampleTable 1 }

       Pd2PowerTrendingSampleEntry ::= SEQUENCE {
                pd2PowerTrendingSampleIndex INTEGER,
                pd2PowerTrendingSampleTimeStamp OCTET STRING,
                pd2PowerTrendingSampleAve OCTET STRING
                }

       pd2PowerTrendingSampleIndex  OBJECT-TYPE
                SYNTAX  Integer32 (0..2147483647) -- was INTEGER
                MAX-ACCESS  read-only
                STATUS  current -- was mandatory
                DESCRIPTION
                "Power Domain 2 Power Trending Sample Table Index."
                ::= { pd2PowerTrendingSampleEntry 1 }

       pd2PowerTrendingSampleTimeStamp  OBJECT-TYPE
                SYNTAX  OCTET STRING
                MAX-ACCESS  read-only
                STATUS  current -- was mandatory
                DESCRIPTION
                "Power Domain 2 Power Trending Sample Table Timestamp."
                ::= { pd2PowerTrendingSampleEntry 2 }

       pd2PowerTrendingSampleAve  OBJECT-TYPE
                SYNTAX  OCTET STRING
                MAX-ACCESS  read-only
                STATUS  current -- was mandatory
                DESCRIPTION
                "Power Domain 2 Power Trending Sample Table Average Power."
                ::= { pd2PowerTrendingSampleEntry 3 }

     moduleInformation  OBJECT IDENTIFIER ::= { fuelGauge 4 }

      bladeDetails  OBJECT IDENTIFIER ::= { moduleInformation 1 } 

       bladeDetailsTable OBJECT-TYPE
                   SYNTAX  SEQUENCE OF BladeDetailsEntry
                   MAX-ACCESS  not-accessible
                   STATUS  current -- was mandatory
                   DESCRIPTION
                   "Table of Blade Module Details."
                   ::= { bladeDetails 1}

       bladeDetailsEntry OBJECT-TYPE
                   SYNTAX BladeDetailsEntry
                   MAX-ACCESS  not-accessible
                   STATUS  current -- was mandatory
                   DESCRIPTION
                   "Blade Module Details entry."
                   INDEX { bladeDetailsIndex }
                   ::= { bladeDetailsTable 1 }

       BladeDetailsEntry ::= SEQUENCE {
                 bladeDetailsIndex INTEGER,
                 bladeDetailsId INTEGER,
                 bladeDetailsMaxPowerConfig INTEGER,
                 bladeDetailsEffectiveClockRate OCTET STRING,
                 bladeDetailsMaximumClockRate OCTET STRING,
                 bladeDetailsPowerSaverMode INTEGER,
                 bladeDetailsDynamicPowerSaver INTEGER,
                 bladeDetailsDynamicPowerFavorPerformanceOverPower INTEGER
                 }
      
       bladeDetailsIndex  OBJECT-TYPE
                 SYNTAX  Integer32 (0..2147483647) -- was INTEGER
                 MAX-ACCESS  read-only
                 STATUS  current -- was mandatory
                 DESCRIPTION
                 "Blade Module Details Table Index."
                 ::= { bladeDetailsEntry 1 }

       bladeDetailsId  OBJECT-TYPE
                   SYNTAX  INTEGER {
                       blade1(1),
                       blade2(2),
                       blade3(3),
                       blade4(4),
                       blade5(5),
                       blade6(6),
                       blade7(7),
                       blade8(8),
                       blade9(9),
                       blade10(10),
                       blade11(11),
                       blade12(12),
                       blade13(13),
                       blade14(14)
                     }
                   MAX-ACCESS  read-only
                   STATUS  current -- was mandatory
                   DESCRIPTION
                   "Blade Module Details Table Blade Id."
                 ::= { bladeDetailsEntry 2 }
                 
       bladeDetailsMaxPowerConfig  OBJECT-TYPE
                 SYNTAX  INTEGER
                 MAX-ACCESS  read-write
                 STATUS  current -- was mandatory
                 DESCRIPTION
                 "Blade Module Details Table Maximum Power Configuration.
                 Allow the user to set the maximum power that can be used by the blade. This
                 function is also known as power capping.

                 If the value of maximum power config is zero, it means the blade doesn't 
                 support the power capping feature"
                 ::= { bladeDetailsEntry 3 }

       bladeDetailsEffectiveClockRate  OBJECT-TYPE
                 SYNTAX  OCTET STRING
                 MAX-ACCESS  read-only
                 STATUS  current -- was mandatory
                 DESCRIPTION
                 "Blade Module Details Table Effective CPU Clock Rate applies to DPM  
                 blades only.  It displays processor's effective clock rate based  
                 on sample interval.  Note that some blades do not effective  
                 clock rate.  In this case, 'notApplicable' will be displayed.
                 When a 1200W or 1400W power module is installed in the domain 
                 the power management policy will not be applicable. 
                 In addition the power consumption in this domain will not be monitored.
           
                 NOTE: The effective clock rate are reported only on a primary slot when 
                 a server blade spans multiple slots (e.g. double wide or 
                 triple wide).  For example if the blade is double wide and 
                 is installed in slot 3 and 4.  3 is primary slot while 4 is not.
                 The effective clock rate are reported on slot 3 while 'notApplicable' 
                 is displayed for slot 4." 
                 ::= { bladeDetailsEntry 4 }  
                 
       bladeDetailsMaximumClockRate  OBJECT-TYPE
                 SYNTAX  OCTET STRING
                 MAX-ACCESS  read-only
                 STATUS  current -- was mandatory
                 DESCRIPTION
                 "Blade Module Details Table Maximum CPU Clock Rate applies to DPM  
                 blades only.  It displays processor's maximum clock rate based  
                 on sample interval.  Note that some blades do not maximum  
                 clock rate.  In this case, 'notApplicable' will be displayed.
                 When a 1200W or 1400W power module is installed in the domain 
                 the power management policy will not be applicable. 
                 In addition the power consumption in this domain will not be monitored.
           
                 NOTE: The maximum clock rate are reported only on a primary slot when 
                 a server blade spans multiple slots (e.g. double wide or 
                 triple wide).  For example if the blade is double wide and 
                 is installed in slot 3 and 4.  3 is primary slot while 4 is not.
                 The maximum clock rate are reported on slot 3 while 'notApplicable' 
                 is displayed for slot 4." 
                 ::= { bladeDetailsEntry 5 }                            

       bladeDetailsPowerSaverMode OBJECT-TYPE  
                 SYNTAX  INTEGER {
                         disable(0),
                         enable(1),
                         notApplicable(255)
                 }
                 MAX-ACCESS  read-write
                 STATUS  current -- was mandatory
                 DESCRIPTION
                 "When enabled, the static low power saver mode allows the blade to selectively
                 alter its operating voltage and frequency to reduce power consumption.
                 This feature is not available on all blade types.  Please refer to the blade documentation for details.
                 If a blade does not support the static low power saver mode, this object will return notApplicable (255).
                 
                 Under certain rare circumstances, the enabling of the static low power saver mode
                 may not complete successfully due to interactions with other
                 blade functions, such as BIOS. Therefore, it is highly recommended that 
                 the user perform a GET of this object after performing a SET, in order
                 to verify the completion of the intended operation."
                 ::= { bladeDetailsEntry 6 }                           
                 
       bladeDetailsDynamicPowerSaver OBJECT-TYPE  
                 SYNTAX  INTEGER {
                         disable(0),
                         enable(1),
                         notApplicable(255)
                 }
                 MAX-ACCESS  read-write
                 STATUS  current -- was mandatory
                 DESCRIPTION
                 "When enabled, Dynamic Power Saver allows the voltage and frequency of the CPUs on the blade 
                 to be controlled based on how busy the CPU is.  This feature is not available on all blade types.  
                 Please refer to the blade documentation for details.  If a blade does not support the dynamic power 
                 saver, this object will return notApplicable (255).

                 Under certain rare circumstances, the enabling of the dynamic power saver may not complete 
                 successfully due to interactions with other blade functions, such as BIOS. Therefore, it is 
                 highly recommended that the user perform a GET of this object after performing a SET, in order
                 to verify the completion of the intended operation."
                 ::= { bladeDetailsEntry 7 }  

       bladeDetailsDynamicPowerFavorPerformanceOverPower OBJECT-TYPE  
                 SYNTAX  INTEGER {
                         disable(0),
                         enable(1),
                         notApplicable(255)
                 }
                 MAX-ACCESS  read-write
                 STATUS  current -- was mandatory
                 DESCRIPTION
                 "When enabled, Dynamic Power Favor Performance Over Power supports a max performance mode that pushes the 
                 system past its nominal CPU frequency when CPU and memory utilization implies it would help and the 
                 system allows it.  Dynamic Power Performance Over Power can be active on the blade only after Dynamic 
                 Power Saver is enabled.  This feature is not available on all blade types.  Please refer to the 
                 blade documentation for details.  If a blade does not support the dynamic power saver, this object 
                 will return notApplicable (255).
                 
                 Under certain rare circumstances, the enabling of the dynamic power favor performance over power
                 may not complete successfully due to interactions with other blade functions, such as BIOS. 
                 Therefore, it is highly recommended that the user perform a GET of this object after performing a SET, 
                 in order to verify the completion of the intended operation."
                 ::= { bladeDetailsEntry 8 }  

       bladePowerTrending  OBJECT IDENTIFIER ::= { bladeDetails 3 } 
      
        bladePowerTrendingPeriod  OBJECT-TYPE
                 SYNTAX  INTEGER  {
                        lastHour(0),
                        last6Hours(1),
                        last12Hours(2),
                        last24Hours(3)
                 }
                 MAX-ACCESS  read-write
                 STATUS  current -- was mandatory
                 DESCRIPTION
                 "Specify time period for blade module power trending information table view.

                 NOTE: This time period should be configured before displaying the
                 following Power Trending Information table for Blade Module."
                 ::= { bladePowerTrending 1 } 

        bladePowerTrendingBladeId  OBJECT-TYPE
                   SYNTAX  INTEGER {
                       blade1(1),
                       blade2(2),
                       blade3(3),
                       blade4(4),
                       blade5(5),
                       blade6(6),
                       blade7(7),
                       blade8(8),
                       blade9(9),
                       blade10(10),
                       blade11(11),
                       blade12(12),
                       blade13(13),
                       blade14(14)
                     }
                   MAX-ACCESS  read-write
                   STATUS  current -- was mandatory
                   DESCRIPTION
                   "Blade Module Power Trending Blade Id.
                   
                   NOTE: The Blade Id should be configured before displaying the 
                   bladePowerTrendingTable."
                   ::= { bladePowerTrending 2 }
                 
        bladePowerTrendingSampleTable  OBJECT-TYPE
                SYNTAX  SEQUENCE OF BladePowerTrendingSampleEntry
                MAX-ACCESS  not-accessible
                STATUS  current -- was mandatory
                DESCRIPTION
                "Table of Blade Module Power Trending Information."
                ::= { bladePowerTrending 10 }

        bladePowerTrendingSampleEntry OBJECT-TYPE
                SYNTAX  BladePowerTrendingSampleEntry
                MAX-ACCESS  not-accessible
                STATUS  current -- was mandatory
                DESCRIPTION
                "Blade Module Power Trending Sample entry."
                INDEX { bladePowerTrendingSampleIndex }
                ::= { bladePowerTrendingSampleTable 1 }

        BladePowerTrendingSampleEntry ::= SEQUENCE {
                bladePowerTrendingSampleIndex INTEGER,
                bladePowerTrendingSampleId INTEGER,
                bladePowerTrendingSampleTimeStamp OCTET STRING,                
                bladePowerTrendingSampleMax OCTET STRING,
                bladePowerTrendingSampleMin OCTET STRING,
                bladePowerTrendingSampleAve OCTET STRING
                }

        bladePowerTrendingSampleIndex  OBJECT-TYPE
                SYNTAX  Integer32 (0..2147483647) -- was INTEGER
                MAX-ACCESS  read-only
                STATUS  current -- was mandatory
                DESCRIPTION
                "Blade Module Power Trending Sample Table Index."
                ::= { bladePowerTrendingSampleEntry 1 }

        bladePowerTrendingSampleId  OBJECT-TYPE
                   SYNTAX  INTEGER {
                       blade1(1),
                       blade2(2),
                       blade3(3),
                       blade4(4),
                       blade5(5),
                       blade6(6),
                       blade7(7),
                       blade8(8),
                       blade9(9),
                       blade10(10),
                       blade11(11),
                       blade12(12),
                       blade13(13),
                       blade14(14)
                     }
                   MAX-ACCESS  read-only
                   STATUS  current -- was mandatory
                   DESCRIPTION
                   "Blade Module Power Trending Sample Table Blade Id."
                   ::= { bladePowerTrendingSampleEntry 2 }
                 
        bladePowerTrendingSampleTimeStamp  OBJECT-TYPE
                SYNTAX  OCTET STRING
                MAX-ACCESS  read-only
                STATUS  current -- was mandatory
                DESCRIPTION
                "Blade Module Power Trending Sample Table  Timestamp."
                ::= { bladePowerTrendingSampleEntry 3 }

        bladePowerTrendingSampleMax  OBJECT-TYPE
                SYNTAX  OCTET STRING
                MAX-ACCESS  read-only
                STATUS  current -- was mandatory
                DESCRIPTION
                "Blade Module Power Trending Sample Table Maximum Power."
                ::= { bladePowerTrendingSampleEntry 4 }

        bladePowerTrendingSampleMin  OBJECT-TYPE
                SYNTAX  OCTET STRING
                MAX-ACCESS  read-only
                STATUS  current -- was mandatory
                DESCRIPTION
                "Blade Module Power Trending Sample Table Minimum Power."
                ::= { bladePowerTrendingSampleEntry 5 }

        bladePowerTrendingSampleAve  OBJECT-TYPE
                SYNTAX  OCTET STRING
                MAX-ACCESS  read-only
                STATUS  current -- was mandatory
                DESCRIPTION
                "Blade Module Power Trending Sample Table Average Power."
                ::= { bladePowerTrendingSampleEntry 6 }


      switchDetails  OBJECT IDENTIFIER ::= { moduleInformation 2 } 

       switchPowerTrending  OBJECT IDENTIFIER ::= { switchDetails 3 } 
      
        switchPowerTrendingPeriod  OBJECT-TYPE
                 SYNTAX  INTEGER  {
                        lastHour(0),
                        last6Hours(1),
                        last12Hours(2),
                        last24Hours(3)
                 }
                 MAX-ACCESS  read-write
                 STATUS  current -- was mandatory
                 DESCRIPTION
                 "Specify time period for switch module power trending information table view.

                 NOTE: This time period should be configured before displaying the
                 following Power Trending Information table for Switch Module."
                 ::= { switchPowerTrending 1 } 

        switchPowerTrendingSwitchId  OBJECT-TYPE
                   SYNTAX  INTEGER {
                        module1(1),
                        module2(2),
                        module3(3),
                        module4(4),
                        module5(5),
                        module6(6),
                        module7(7),
                        module8(8),
                        module9(9),
                        module10(10)
                     }
                   MAX-ACCESS  read-write
                   STATUS  current -- was mandatory
                   DESCRIPTION
                   "Switch Module Power Trending Switch Id.
                   
                   NOTE: The Switch Id should be configured before displaying the 
                   switchPowerTrendingTable."
                   ::= { switchPowerTrending 2 }
                 
       switchPowerTrendingSampleTable  OBJECT-TYPE
                SYNTAX  SEQUENCE OF SwitchPowerTrendingSampleEntry
                MAX-ACCESS  not-accessible
                STATUS  current -- was mandatory
                DESCRIPTION
                "Table of Switch Module Power Trending Information."
                ::= { switchPowerTrending 10 }

       switchPowerTrendingSampleEntry OBJECT-TYPE
                SYNTAX  SwitchPowerTrendingSampleEntry
                MAX-ACCESS  not-accessible
                STATUS  current -- was mandatory
                DESCRIPTION
                "Switch Module Power Trending Sample entry."
                INDEX { switchPowerTrendingSampleIndex }
                ::= { switchPowerTrendingSampleTable 1 }

       SwitchPowerTrendingSampleEntry ::= SEQUENCE {
                switchPowerTrendingSampleIndex INTEGER,
                switchPowerTrendingSampleId INTEGER,
                switchPowerTrendingSampleTimeStamp OCTET STRING,                
                switchPowerTrendingSampleMax OCTET STRING,
                switchPowerTrendingSampleMin OCTET STRING,
                switchPowerTrendingSampleAve OCTET STRING
                }

       switchPowerTrendingSampleIndex  OBJECT-TYPE
                SYNTAX  Integer32 (0..2147483647) -- was INTEGER
                MAX-ACCESS  read-only
                STATUS  current -- was mandatory
                DESCRIPTION
                "Switch Module Power Trending Sample Table Index."
                ::= { switchPowerTrendingSampleEntry 1 }

       switchPowerTrendingSampleId  OBJECT-TYPE
                   SYNTAX  INTEGER {
                       module1(1),
                       module2(2),
                       module3(3),
                       module4(4),
                       module5(5),
                       module6(6),
                       module7(7),
                       module8(8),
                       module9(9),
                       module10(10)
                     }
                   MAX-ACCESS  read-only
                   STATUS  current -- was mandatory
                   DESCRIPTION
                   "Switch Module Power Trending Sample Table Switch Id."
                   ::= { switchPowerTrendingSampleEntry 2 }
                 
       switchPowerTrendingSampleTimeStamp  OBJECT-TYPE
                SYNTAX  OCTET STRING
                MAX-ACCESS  read-only
                STATUS  current -- was mandatory
                DESCRIPTION
                "Switch Module Power Trending Sample Table  Timestamp."
                ::= { switchPowerTrendingSampleEntry 3 }

       switchPowerTrendingSampleMax  OBJECT-TYPE
                SYNTAX  OCTET STRING
                MAX-ACCESS  read-only
                STATUS  current -- was mandatory
                DESCRIPTION
                "Switch Module Power Trending Sample Table Maximum Power."
                ::= { switchPowerTrendingSampleEntry 4 }

       switchPowerTrendingSampleMin  OBJECT-TYPE
                SYNTAX  OCTET STRING
                MAX-ACCESS  read-only
                STATUS  current -- was mandatory
                DESCRIPTION
                "Switch Module Power Trending Sample Table Minimum Power."
                ::= { switchPowerTrendingSampleEntry 5 }

       switchPowerTrendingSampleAve  OBJECT-TYPE
                SYNTAX  OCTET STRING
                MAX-ACCESS  read-only
                STATUS  current -- was mandatory
                DESCRIPTION
                "Switch Module Power Trending Sample Table Average Power."
                ::= { switchPowerTrendingSampleEntry 6 }      


      blowerDetails  OBJECT IDENTIFIER ::= { moduleInformation 3 } 

       blowerPowerTrending  OBJECT IDENTIFIER ::= { blowerDetails 3 } 
      
        blowerPowerTrendingPeriod  OBJECT-TYPE
                 SYNTAX  INTEGER  {
                        lastHour(0),
                        last6Hours(1),
                        last12Hours(2),
                        last24Hours(3)
                 }
                 MAX-ACCESS  read-write
                 STATUS  current -- was mandatory
                 DESCRIPTION
                 "Specify time period for blower module power trending information table view.

                 NOTE: This time period should be configured before displaying the
                 following Power Trending Information table for Blower Module.
                 NOTE: Blowers are also referred to as Chassis Cooling Devices."
                 ::= { blowerPowerTrending 1 } 

        blowerPowerTrendingBlowerId  OBJECT-TYPE
                   SYNTAX  INTEGER {
                        blower1(1),
                        blower2(2),
                        blower3(3),
                        blower4(4)
                     }
                   MAX-ACCESS  read-write
                   STATUS  current -- was mandatory
                   DESCRIPTION
                   "Blower Module Power Trending Blower Id.
                   
                   NOTE: The Blower Id should be configured before displaying the blowerPowerTrendingTable.
                   NOTE: Blowers are also referred to as Chassis Cooling Devices."
                   ::= { blowerPowerTrending 2 }
                 
       blowerPowerTrendingSampleTable  OBJECT-TYPE
                SYNTAX  SEQUENCE OF BlowerPowerTrendingSampleEntry
                MAX-ACCESS  not-accessible
                STATUS  current -- was mandatory
                DESCRIPTION
                "Table of Blower Module Power Trending Information.

                NOTE: Blowers are also referred to as Chassis Cooling Devices."
                ::= { blowerPowerTrending 10 }

       blowerPowerTrendingSampleEntry OBJECT-TYPE
                SYNTAX  BlowerPowerTrendingSampleEntry
                MAX-ACCESS  not-accessible
                STATUS  current -- was mandatory
                DESCRIPTION
                "Blower Module Power Trending Sample entry."
                INDEX { blowerPowerTrendingSampleIndex }
                ::= { blowerPowerTrendingSampleTable 1 }

       BlowerPowerTrendingSampleEntry ::= SEQUENCE {
                blowerPowerTrendingSampleIndex INTEGER,
                blowerPowerTrendingSampleId INTEGER,
                blowerPowerTrendingSampleTimeStamp OCTET STRING,                
                blowerPowerTrendingSampleMax OCTET STRING,
                blowerPowerTrendingSampleMin OCTET STRING,
                blowerPowerTrendingSampleAve OCTET STRING
                }

       blowerPowerTrendingSampleIndex  OBJECT-TYPE
                SYNTAX  Integer32 (0..2147483647) -- was INTEGER
                MAX-ACCESS  read-only
                STATUS  current -- was mandatory
                DESCRIPTION
                "Blower Module Power Trending Sample Table Index."
                ::= { blowerPowerTrendingSampleEntry 1 }

       blowerPowerTrendingSampleId  OBJECT-TYPE
                   SYNTAX  INTEGER {
                       blower1(1),
                       blower2(2),
                       blower3(3),
                       blower4(4)
                     }
                   MAX-ACCESS  read-only
                   STATUS  current -- was mandatory
                   DESCRIPTION
                   "Blower Module Power Trending Sample Table Blower Id."
                   ::= { blowerPowerTrendingSampleEntry 2 }
                 
       blowerPowerTrendingSampleTimeStamp  OBJECT-TYPE
                SYNTAX  OCTET STRING
                MAX-ACCESS  read-only
                STATUS  current -- was mandatory
                DESCRIPTION
                "Blower Module Power Trending Sample Table Timestamp."
                ::= { blowerPowerTrendingSampleEntry 3 }

       blowerPowerTrendingSampleMax  OBJECT-TYPE
                SYNTAX  OCTET STRING
                MAX-ACCESS  read-only
                STATUS  current -- was mandatory
                DESCRIPTION
                "Blower Module Power Trending Sample Table Maximum Power."
                ::= { blowerPowerTrendingSampleEntry 4 }

       blowerPowerTrendingSampleMin  OBJECT-TYPE
                SYNTAX  OCTET STRING
                MAX-ACCESS  read-only
                STATUS  current -- was mandatory
                DESCRIPTION
                "Blower Module Power Trending Sample Table Minimum Power."
                ::= { blowerPowerTrendingSampleEntry 5 }

       blowerPowerTrendingSampleAve  OBJECT-TYPE
                SYNTAX  OCTET STRING
                MAX-ACCESS  read-only
                STATUS  current -- was mandatory
                DESCRIPTION
                "Blower Module Power Trending Sample Table Average Power."
                ::= { blowerPowerTrendingSampleEntry 6 }      

      -- ******************************************************************************
      -- Chassis Global Information
      -- ******************************************************************************

     chassisInformation  OBJECT IDENTIFIER ::= { fuelGauge 5 }

      chassisConfiguration  OBJECT IDENTIFIER ::= { chassisInformation 1 }

       chassisTotalDCPowerAvailable  OBJECT-TYPE
                SYNTAX  OCTET STRING
                MAX-ACCESS  read-only
                STATUS  current -- was mandatory
                DESCRIPTION
                "Chassis total DC power available, which displays the total DC power available 
                for the entire chassis. It is the sum of the two power domains."
                ::= { chassisConfiguration 1 }

       chassisTotalACPowerInUsed  OBJECT-TYPE
                SYNTAX  OCTET STRING
                MAX-ACCESS  read-only
                STATUS  current -- was mandatory
                DESCRIPTION
                "Chassis total AC power being used, which displays the total AC power 
                being consumed by all modules in the chassis. It also includes power 
                consumed by the blowers (chassis oooling devices) for the chassis."
                ::= { chassisConfiguration 2 }
                
       chassisTotalThermalOutput  OBJECT-TYPE
                SYNTAX  OCTET STRING
                MAX-ACCESS  read-only
                STATUS  current -- was mandatory
                DESCRIPTION
                "Chassis total thermal output, which displays the thermal output
                (load) in BTUs per hour. It is calculated based on the total AC
                power in use. (1 Watt = 3.412 BTU/hour)."
                ::= { chassisConfiguration 3 }

       chassisTrendingSampleInterval  OBJECT-TYPE
                SYNTAX  INTEGER 
                MAX-ACCESS  read-write
                STATUS  current -- was mandatory
                DESCRIPTION
                "Chassis Power and Thermal Trending Sample Interval.
                0 means no trending. the minimum interval is 10 minutes and the maximum 
                is 60 minutes, in 5 minute increments."
                ::= { chassisConfiguration 4 }

       chassisPowerService OBJECT-TYPE
                 SYNTAX  INTEGER {
                     volt110(1),
                     volt220(2),
                     notAvailable(255)
                 }
                 MAX-ACCESS  read-only
                 STATUS  current -- was mandatory
                 DESCRIPTION
                 "The chassis power service mode.

                 NOTE: This MIB object is for BCS only."
                 ::= { chassisConfiguration 5 }

      -- ******************************************************************************
      -- Chassis Power Trending Information
      -- ******************************************************************************
      chassisPowerTrending  OBJECT IDENTIFIER ::= { chassisInformation 3 }

       chassisPowerTrendingPeriod  OBJECT-TYPE
                 SYNTAX  INTEGER  {
                        lastHour(0),
                        last6Hours(1),
                        last12Hours(2),
                        last24Hours(3)
                 }
                 MAX-ACCESS  read-write
                 STATUS  current -- was mandatory
                 DESCRIPTION
                 "Specify time period of power trending information.
                 NOTE: This time period should be configured before displaying the
                 following Power Trending Information table for Chassis."                 
                 ::= { chassisPowerTrending 1 } 
                
       chassisPowerTrendingSampleTable  OBJECT-TYPE
                SYNTAX  SEQUENCE OF ChassisPowerTrendingSampleEntry
                MAX-ACCESS  not-accessible
                STATUS  current -- was mandatory
                DESCRIPTION
                "Table of Chassis Power Trending Sample Information in specified time period."
                ::= { chassisPowerTrending 10 }

       chassisPowerTrendingSampleEntry OBJECT-TYPE
                SYNTAX ChassisPowerTrendingSampleEntry
                MAX-ACCESS  not-accessible
                STATUS  current -- was mandatory
                DESCRIPTION
                "Chassis Power Trending Sample entry in specified time period."
                INDEX { chassisPowerTrendingSampleIndex }
                ::= { chassisPowerTrendingSampleTable 1 }

       ChassisPowerTrendingSampleEntry ::= SEQUENCE {
                chassisPowerTrendingSampleIndex INTEGER,
                chassisPowerTrendingSampleTimeStamp OCTET STRING,
                chassisPowerTrendingSampleAve OCTET STRING
                }

       chassisPowerTrendingSampleIndex  OBJECT-TYPE
                SYNTAX  Integer32 (0..2147483647) -- was INTEGER
                MAX-ACCESS  read-only
                STATUS  current -- was mandatory
                DESCRIPTION
                "Chassis Power Trending Sample Index in specified time period."
                ::= { chassisPowerTrendingSampleEntry 1 }

       chassisPowerTrendingSampleTimeStamp  OBJECT-TYPE
                SYNTAX  OCTET STRING
                MAX-ACCESS  read-only
                STATUS  current -- was mandatory
                DESCRIPTION
                "Chassis Power Trending Sample Timestamp in specified time period."
                ::= { chassisPowerTrendingSampleEntry 2 }

       chassisPowerTrendingSampleAve  OBJECT-TYPE
                SYNTAX  OCTET STRING
                MAX-ACCESS  read-only
                STATUS  current -- was mandatory
                DESCRIPTION
                "Chassis Power Trending Sample Average Power in specified time period."
                ::= { chassisPowerTrendingSampleEntry 3 }

      -- ******************************************************************************
      -- Chassis Thermal Trending Information
      -- ******************************************************************************
      chassisThermalTrending  OBJECT IDENTIFIER ::= { chassisInformation 5 }

       chassisThermalTrendingPeriod  OBJECT-TYPE
                 SYNTAX  INTEGER  {
                        lastHour(0),
                        last6Hours(1),
                        last12Hours(2),
                        last24Hours(3)
                 }
                 MAX-ACCESS  read-write
                 STATUS  current -- was mandatory
                 DESCRIPTION
                 "Specify time period of thermal trending information.
                 NOTE: This time period should be configured before displaying the
                 following Thermal Trending Information table for Chassis."
                 ::= { chassisThermalTrending 1 } 

        mt1ThermalTrendingTable  OBJECT-TYPE
                SYNTAX  SEQUENCE OF Mt1ThermalTrendingEntry
                MAX-ACCESS  not-accessible
                STATUS  current -- was mandatory
                DESCRIPTION
                "Table of Media Tray 1 Thermal Trending Information."
                ::= { chassisThermalTrending 10 }

        mt1ThermalTrendingEntry OBJECT-TYPE
                SYNTAX Mt1ThermalTrendingEntry
                MAX-ACCESS  not-accessible
                STATUS  current -- was mandatory
                DESCRIPTION
                "Media Tray 1 Thermal Trending entry."
                INDEX { mt1ThermalTrendingIndex }
                ::= { mt1ThermalTrendingTable 1 }

        Mt1ThermalTrendingEntry ::= SEQUENCE {
                mt1ThermalTrendingIndex INTEGER,
                mt1ThermalTrendingTimeStamp OCTET STRING,
                mt1ThermalTrendingTemperature OCTET STRING
                }

        mt1ThermalTrendingIndex  OBJECT-TYPE
                SYNTAX  Integer32 (0..2147483647) -- was INTEGER
                MAX-ACCESS  read-only
                STATUS  current -- was mandatory
                DESCRIPTION
                "Media Tray 1 Thermal Trending Table Index."
                ::= { mt1ThermalTrendingEntry 1 }

        mt1ThermalTrendingTimeStamp  OBJECT-TYPE
                SYNTAX  OCTET STRING
                MAX-ACCESS  read-only
                STATUS  current -- was mandatory
                DESCRIPTION
                "Media Tray 1 Thermal Trending Table Sample Timestamp."
                ::= { mt1ThermalTrendingEntry 2 }

        mt1ThermalTrendingTemperature  OBJECT-TYPE
                 SYNTAX  OCTET STRING
                 MAX-ACCESS  read-only
                 STATUS  current -- was mandatory
                 DESCRIPTION
                 "Media Tray 1 Thermal Trending Table Temperature."
                 ::= { mt1ThermalTrendingEntry 3 }

        mt2ThermalTrendingTable  OBJECT-TYPE
                SYNTAX  SEQUENCE OF Mt2ThermalTrendingEntry
                MAX-ACCESS  not-accessible
                STATUS  current -- was mandatory
                DESCRIPTION
                "Table of Media Tray 2 Thermal Trending Information.
                
                NOTE: This MIB object is for BladeCenter HT only."
                ::= { chassisThermalTrending 15 }

        mt2ThermalTrendingEntry OBJECT-TYPE
                SYNTAX Mt2ThermalTrendingEntry
                MAX-ACCESS  not-accessible
                STATUS  current -- was mandatory
                DESCRIPTION
                "Media Tray 2 Thermal Trending entry.
                
                NOTE: This MIB object is for BladeCenter HT only."
                INDEX { mt2ThermalTrendingIndex }
                ::= { mt2ThermalTrendingTable 1 }

        Mt2ThermalTrendingEntry ::= SEQUENCE {
                mt2ThermalTrendingIndex INTEGER,
                mt2ThermalTrendingTimeStamp OCTET STRING,
                mt2ThermalTrendingTemperature OCTET STRING
                }

        mt2ThermalTrendingIndex  OBJECT-TYPE
                SYNTAX  Integer32 (0..2147483647) -- was INTEGER
                MAX-ACCESS  read-only
                STATUS  current -- was mandatory
                DESCRIPTION
                "Media Tray 2 Thermal Trending Table Index.

                NOTE: This MIB object is for BladeCenter HT only."
                ::= { mt2ThermalTrendingEntry 1 }

        mt2ThermalTrendingTimeStamp  OBJECT-TYPE
                SYNTAX  OCTET STRING
                MAX-ACCESS  read-only
                STATUS  current -- was mandatory
                DESCRIPTION
                "Media Tray 2 Thermal Trending Table Sample Timestamp.

                NOTE: This MIB object is for BladeCenter HT only."
                ::= { mt2ThermalTrendingEntry 2 }

        mt2ThermalTrendingTemperature  OBJECT-TYPE
                 SYNTAX  OCTET STRING
                 MAX-ACCESS  read-only
                 STATUS  current -- was mandatory
                 DESCRIPTION
                 "Media Tray 2 Thermal Trending Table Temperature.
                 
                 NOTE: This MIB object is for BladeCenter HT only."
                 ::= { mt2ThermalTrendingEntry 3 }

        blower1ThermalTrendingTable  OBJECT-TYPE
                SYNTAX  SEQUENCE OF Blower1ThermalTrendingEntry
                MAX-ACCESS  not-accessible
                STATUS  current -- was mandatory
                DESCRIPTION
                "Table of Blower 1 Thermal Trending Information.

                NOTE: Blowers are also referred to as Chassis Cooling Devices."
                ::= { chassisThermalTrending 20}

        blower1ThermalTrendingEntry OBJECT-TYPE
                SYNTAX Blower1ThermalTrendingEntry
                MAX-ACCESS  not-accessible
                STATUS  current -- was mandatory
                DESCRIPTION
                "Blower 1 Thermal Trending entry."
                INDEX { blower1ThermalTrendingIndex }
                ::= { blower1ThermalTrendingTable 1 }

        Blower1ThermalTrendingEntry ::= SEQUENCE {
                blower1ThermalTrendingIndex INTEGER,
                blower1ThermalTrendingTimeStamp OCTET STRING,
                blower1ThermalTrendingTemperature OCTET STRING
                }

        blower1ThermalTrendingIndex  OBJECT-TYPE
                SYNTAX  Integer32 (0..2147483647) -- was INTEGER
                MAX-ACCESS  read-only
                STATUS  current -- was mandatory
                DESCRIPTION
                "Blower 1 Thermal Trending Table Index."
                ::= { blower1ThermalTrendingEntry 1 }

        blower1ThermalTrendingTimeStamp  OBJECT-TYPE
                SYNTAX  OCTET STRING
                MAX-ACCESS  read-only
                STATUS  current -- was mandatory
                DESCRIPTION
                "Blower 1 Thermal Trending Table Sample Timestamp."
                ::= { blower1ThermalTrendingEntry 2 }

        blower1ThermalTrendingTemperature  OBJECT-TYPE
                 SYNTAX  OCTET STRING
                 MAX-ACCESS  read-only
                 STATUS  current -- was mandatory
                 DESCRIPTION
                 "Blower 1 Thermal Trending Table Temperature."
                 ::= { blower1ThermalTrendingEntry 3 }    
                                         
        blower2ThermalTrendingTable  OBJECT-TYPE
                SYNTAX  SEQUENCE OF Blower2ThermalTrendingEntry
                MAX-ACCESS  not-accessible
                STATUS  current -- was mandatory
                DESCRIPTION
                "Table of Blower 2 Thermal Trending Information.

                NOTE: Blowers are also referred to as Chassis Cooling Devices."
                ::= { chassisThermalTrending 30}

        blower2ThermalTrendingEntry OBJECT-TYPE
                SYNTAX Blower2ThermalTrendingEntry
                MAX-ACCESS  not-accessible
                STATUS  current -- was mandatory
                DESCRIPTION
                "Blower Thermal 2 Trending entry."
                INDEX { blower2ThermalTrendingIndex }
                ::= { blower2ThermalTrendingTable 1 }

        Blower2ThermalTrendingEntry ::= SEQUENCE {
                blower2ThermalTrendingIndex INTEGER,
                blower2ThermalTrendingTimeStamp OCTET STRING,
                blower2ThermalTrendingTemperature OCTET STRING
                }

        blower2ThermalTrendingIndex  OBJECT-TYPE
                SYNTAX  Integer32 (0..2147483647) -- was INTEGER
                MAX-ACCESS  read-only
                STATUS  current -- was mandatory
                DESCRIPTION
                "Blower 2 Thermal Trending Table Index."
                ::= { blower2ThermalTrendingEntry 1 }

        blower2ThermalTrendingTimeStamp  OBJECT-TYPE
                SYNTAX  OCTET STRING
                MAX-ACCESS  read-only
                STATUS  current -- was mandatory
                DESCRIPTION
                "Blower 2 Thermal Trending Table Sample Timestamp."
                ::= { blower2ThermalTrendingEntry 2 }

        blower2ThermalTrendingTemperature  OBJECT-TYPE
                 SYNTAX  OCTET STRING
                 MAX-ACCESS  read-only
                 STATUS  current -- was mandatory
                 DESCRIPTION
                 "Blower 2 Thermal Trending Table Temperature."
                 ::= { blower2ThermalTrendingEntry 3 }         
                 
        blower3ThermalTrendingTable  OBJECT-TYPE
                SYNTAX  SEQUENCE OF Blower3ThermalTrendingEntry
                MAX-ACCESS  not-accessible
                STATUS  current -- was mandatory
                DESCRIPTION
                "Table of Blower 3 Thermal Trending Information.

                NOTE: This MIB object is for BladeCenter T only.
                NOTE: Blowers are also referred to as Chassis Cooling Devices."
                ::= { chassisThermalTrending 40}

        blower3ThermalTrendingEntry OBJECT-TYPE
                SYNTAX Blower3ThermalTrendingEntry
                MAX-ACCESS  not-accessible
                STATUS  current -- was mandatory
                DESCRIPTION
                "Blower 3 Thermal Trending entry.

                NOTE: This MIB object is for BladeCenter T only."
                INDEX { blower3ThermalTrendingIndex }
                ::= { blower3ThermalTrendingTable 1 }

        Blower3ThermalTrendingEntry ::= SEQUENCE {
                blower3ThermalTrendingIndex INTEGER,
                blower3ThermalTrendingTimeStamp OCTET STRING,
                blower3ThermalTrendingTemperature OCTET STRING
                }

        blower3ThermalTrendingIndex  OBJECT-TYPE
                SYNTAX  Integer32 (0..2147483647) -- was INTEGER
                MAX-ACCESS  read-only
                STATUS  current -- was mandatory
                DESCRIPTION
                "Blower 3 Thermal Trending Table Index.

                NOTE: This MIB object is for BladeCenter T only."
                ::= { blower3ThermalTrendingEntry 1 }

        blower3ThermalTrendingTimeStamp  OBJECT-TYPE
                SYNTAX  OCTET STRING
                MAX-ACCESS  read-only
                STATUS  current -- was mandatory
                DESCRIPTION
                "Blower 3 Thermal Trending Table Sample Timestamp.

                NOTE: This MIB object is for BladeCenter T only."
                ::= { blower3ThermalTrendingEntry 2 }

        blower3ThermalTrendingTemperature  OBJECT-TYPE
                 SYNTAX  OCTET STRING
                 MAX-ACCESS  read-only
                 STATUS  current -- was mandatory
                 DESCRIPTION
                 "Blower 3 Thermal Trending Table Temperature.

                 NOTE: This MIB object is for BladeCenter T only."
                 ::= { blower3ThermalTrendingEntry 3 }    

        blower4ThermalTrendingTable  OBJECT-TYPE
                SYNTAX  SEQUENCE OF Blower4ThermalTrendingEntry
                MAX-ACCESS  not-accessible
                STATUS  current -- was mandatory
                DESCRIPTION
                "Table of Blower 4 Thermal Trending Information.

                NOTE: This MIB object is for BladeCenter T only."
                ::= { chassisThermalTrending 50}

        blower4ThermalTrendingEntry OBJECT-TYPE
                SYNTAX Blower4ThermalTrendingEntry
                MAX-ACCESS  not-accessible
                STATUS  current -- was mandatory
                DESCRIPTION
                "Blower 4 Thermal Trending entry.

                NOTE: This MIB object is for BladeCenter T only.
                NOTE: Blowers are also referred to as Chassis Cooling Devices."
                INDEX { blower4ThermalTrendingIndex }
                ::= { blower4ThermalTrendingTable 1 }

        Blower4ThermalTrendingEntry ::= SEQUENCE {
                blower4ThermalTrendingIndex INTEGER,
                blower4ThermalTrendingTimeStamp OCTET STRING,
                blower4ThermalTrendingTemperature OCTET STRING
                }

        blower4ThermalTrendingIndex  OBJECT-TYPE
                SYNTAX  Integer32 (0..2147483647) -- was INTEGER
                MAX-ACCESS  read-only
                STATUS  current -- was mandatory
                DESCRIPTION
                "Blower 4 Thermal Trending Table Index.

                NOTE: This MIB object is for BladeCenter T only."
                ::= { blower4ThermalTrendingEntry 1 }

        blower4ThermalTrendingTimeStamp  OBJECT-TYPE
                SYNTAX  OCTET STRING
                MAX-ACCESS  read-only
                STATUS  current -- was mandatory
                DESCRIPTION
                "Blower 4 Thermal Trending Table Sample Timestamp.

                NOTE: This MIB object is for BladeCenter T only."
                ::= { blower4ThermalTrendingEntry 2 }

        blower4ThermalTrendingTemperature  OBJECT-TYPE
                 SYNTAX  OCTET STRING
                 MAX-ACCESS  read-only
                 STATUS  current -- was mandatory
                 DESCRIPTION
                 "Blower 4 Thermal Trending Table Temperature.

                 NOTE: This MIB object is for BladeCenter T only."
                 ::= { blower4ThermalTrendingEntry 3 }    
                 
      
   -- ********************************************************************************
   -- Power Policy Table 
   -- ********************************************************************************
      powerPolicyInformation  OBJECT IDENTIFIER ::= { fuelGauge 6 }  
	  
      powerPolicyTable OBJECT-TYPE
                 SYNTAX  SEQUENCE OF PowerPolicyEntry
                 MAX-ACCESS  not-accessible
                 STATUS  current -- was mandatory
                 DESCRIPTION
		 "Table of Power Policy information for all power domains. Reading this 
                  table can tell you about the available power policies that can be 
                  configured for a domain and also which is currently selected. The 
                  powerPolicyActivate object can also be SET to select which policy 
                  should be active for a given power domain."
                 ::= { powerPolicyInformation 1 }

      powerPolicyEntry OBJECT-TYPE
                 SYNTAX  PowerPolicyEntry
                 MAX-ACCESS  not-accessible
                 STATUS  current -- was mandatory
                 DESCRIPTION
                 "Power Policy Entry"
                 INDEX { powerPolicyIndex }
                 ::= { powerPolicyTable 1 }
                   
      PowerPolicyEntry ::= SEQUENCE {
                 powerPolicyIndex INTEGER,
                 powerPolicyPowerDomainNumber INTEGER,
                 powerPolicyName OCTET STRING,
                 powerPolicyPwrSupplyFailureLimit INTEGER,
                 powerPolicyMaxPowerLimit INTEGER,
                 powerPolicyEstimatedUtilization INTEGER,
                 powerPolicyActivate INTEGER
                 }

      powerPolicyIndex  OBJECT-TYPE
                 SYNTAX  Integer32 (0..2147483647) -- was INTEGER
                 MAX-ACCESS  read-only
                 STATUS  current -- was mandatory
                 DESCRIPTION
                 "The unique idenitifier of a row in the powerPolicyTable."
                 ::= { powerPolicyEntry 1 }

      powerPolicyPowerDomainNumber  OBJECT-TYPE
                 SYNTAX  INTEGER {
                   powerDomain1(1), 
                   powerDomain2(2)       
                 }
                 MAX-ACCESS  read-only
                 STATUS  current -- was mandatory
                 DESCRIPTION
                 "The power domain number which this row is associated with."
                 ::= { powerPolicyEntry 2 }
                 
      powerPolicyName  OBJECT-TYPE
                 SYNTAX  OCTET STRING
                 MAX-ACCESS  read-only
                 STATUS  current -- was mandatory
                 DESCRIPTION
  		 "The short name of the power policy. The following are the possible 
                  names and their detailed description:
                  
		  Power Module Redundancy
                        Intended for a single AC power source into the chassis 
                        where each Power Module is on its own dedicated circuit. 
                        Total allowed power draw is limited to one less than the 
                        number of Power Modules when more than one Power Module is 
                        present. One Power Module can fail without affecting blade 
                        operation. Multiple Power Module failures can cause 
                        the chassis to power off. Note that some blades may not be 
                        allowed to power on if doing so would exceed the policy power 
                        limit.
                        
		  Power Module Redundancy with Blade Throttling Allowed
                        Very similar to the Power Module Redundancy policy. This 
                        policy allows you to draw more total power; however, capable 
                        blades may be allowed to throttle down if one Power Module fails.
                        
		  Basic Power Management
                        Total allowed power is higher than other policies and is limited only  
                        by the total power capacity of all the Power Modules up to the maximum 
                        of chassis power rating. This is the least conservative approach, since 
                        it does not provide any protection for AC power source or Power Module 
                        failure. If any single power supply fails, blade and/or chassis 
                        operation may be affected. 
                        
		  AC Power Source Redundancy
                        Intended for dual AC power sources into the chassis. Total 
                        allowed power draw is limited to the capacity of two Power 
                        Modules. This is the most conservative approach and is 
                        recommended when all four Power Modules are installed. 
                        When the chassis is correctly wired with dual AC power 
                        sources, one AC power source can fail without affecting 
                        blade operation. Note that some blades may not be 
                        allowed to power on if doing so would exceed the policy 
                        power limit.
                        
		  AC Power Source Redundancy with Blade Throttling Allowed
                        Very similar to the AC Power Source Redundancy policy. This policy 
                        allows you to draw more total power; however, capable blades 
                        may be allowed to throttle down if one AC power source fails."
                 ::= { powerPolicyEntry 3 }

      powerPolicyPwrSupplyFailureLimit  OBJECT-TYPE
                 SYNTAX  INTEGER
                 MAX-ACCESS  read-only
                 STATUS  current -- was mandatory
                 DESCRIPTION
		 "The maximum number of power supplies that can fail in a chassis 
                  while still providing redundancy."
                 ::= { powerPolicyEntry 4 }

      powerPolicyMaxPowerLimit  OBJECT-TYPE
                 SYNTAX  INTEGER
                 MAX-ACCESS  read-only
                 STATUS  current -- was mandatory
                 DESCRIPTION
		 "The maximum power available (in watts), based on the number of power modules and 
                  the Power Management Policy setting."
                 ::= { powerPolicyEntry 5 }

      powerPolicyEstimatedUtilization  OBJECT-TYPE
                 SYNTAX  INTEGER
                 MAX-ACCESS  read-only
                 STATUS  current -- was mandatory
                 DESCRIPTION
                 "The estimated utilization (as a percentage) based on current power usage."
                 ::= { powerPolicyEntry 6 }

      powerPolicyActivate  OBJECT-TYPE
                 SYNTAX  INTEGER {
                   disabled(0),
                   enabled(1)
                 }
                 MAX-ACCESS  read-write
                 STATUS  current -- was mandatory
                 DESCRIPTION
                 "When read, this object provides the status of this power policy. If the 
                  value is enabled(1), it means this is the active power policy for the 
                  associated domain. When set to a value of enabled(1), the power policy 
                  will be made the active one for the associated domain. A set of disabled(0)
                  is not allowed.
                  
                  The SET may fail when the user goes from a less restrictive policy
                  to a more restrictive policy, e.g. no power management to redundant power 
                  modules.

                  This happens because the AMM might have allocated more power for components 
                  in the less restrictive policy. Then if a user wants to go to a more restrictive 
                  policy, the power available may be lower than what was already allocated. 

                  The SET should always succeed if a user goes from a more restrictive to 
                  a less restrictive policy." 
                 ::= { powerPolicyEntry 7 }

    -- ********************************************************************************
    -- Error logs
    -- ********************************************************************************
    eventLog   OBJECT IDENTIFIER ::= { errorLogs 4 }

     readEventLogTable  OBJECT-TYPE
                    SYNTAX  SEQUENCE OF ReadEventLogEntry
                    MAX-ACCESS  not-accessible
                    STATUS  current -- was mandatory
                    DESCRIPTION
                    "Table of event log entry information."
                    ::= { eventLog 2 }

      readEventLogEntry OBJECT-TYPE
                    SYNTAX ReadEventLogEntry
                    MAX-ACCESS  not-accessible
                    STATUS  current -- was mandatory
                    DESCRIPTION
                    "Event log table entry"
                    INDEX { readEventLogIndex }
                    ::= { readEventLogTable 1 }


      ReadEventLogEntry ::= SEQUENCE {
                  readEventLogIndex INTEGER,
                  readEventLogString OCTET STRING
                  }


      readEventLogIndex  OBJECT-TYPE
                  SYNTAX  Integer32 (0..2147483647) -- was INTEGER
                  MAX-ACCESS  read-only
                  STATUS  current -- was mandatory
                  DESCRIPTION
                  "The event log index number.  
                  For consistent results, view as a table and not as individual entries."
                  ::= { readEventLogEntry 1 }

      readEventLogString OBJECT-TYPE
                  SYNTAX  OCTET STRING
                  MAX-ACCESS  read-only
                  STATUS  current -- was mandatory
                  DESCRIPTION
                  "A string of data detailing an event.  
                  For consistent results, view as a table and not as individual entries."
                  ::= { readEventLogEntry 2 }



     clearEventLog OBJECT-TYPE
                  SYNTAX  INTEGER {
                    execute(1)
                  }
                  MAX-ACCESS  read-write
                  STATUS  current -- was mandatory
                  DESCRIPTION
                  "Clear the event log. 
                  
                  NOTE: Value returned for the GET command is meaningless for this 
                  MIB object."
                  ::= { eventLog 3 }

     monitorLogStateEvents OBJECT-TYPE
                  SYNTAX  INTEGER {
                    disabled(0),
                    enabled(1)
                  }
                  MAX-ACCESS  read-write
                  STATUS  current -- was mandatory
                  DESCRIPTION
                  "If disabled, it means the info LED will not turn on when the log gets full 
                  and no alerts will be sent out. If enabled, the LED will turn on when the log 
                  gets full and alerts will be sent out."
                  ::= { eventLog 4 }

       readEnhancedEventLogTable  OBJECT-TYPE
                    SYNTAX  SEQUENCE OF ReadEnhancedEventLogEntry
                    MAX-ACCESS  not-accessible
                    STATUS  current -- was mandatory
                    DESCRIPTION
                    "Table of enhanced event log entry information."
                    ::= { eventLog 6 }

      readEnhancedEventLogEntry OBJECT-TYPE
                    SYNTAX ReadEnhancedEventLogEntry
                    MAX-ACCESS  not-accessible
                    STATUS  current -- was mandatory
                    DESCRIPTION
                    "Enhaced Event log table entry, new entries could be added for new items."
                    INDEX { readEnhancedEventLogNumber }
                    ::= { readEnhancedEventLogTable 1 }

          ReadEnhancedEventLogEntry ::= SEQUENCE {
                  readEnhancedEventLogNumber INTEGER,
                  readEnhancedEventLogAttribute OCTET STRING,
                  readEnhancedEventLogMessage OCTET STRING
                  }

          readEnhancedEventLogNumber  OBJECT-TYPE
                  SYNTAX  Integer32 (0..2147483647) -- was INTEGER
                  MAX-ACCESS  read-only
                  STATUS  current -- was mandatory
                  DESCRIPTION
                  "The event log number for the enhanced event log.  
                  For consistent results, view as a table and not as individual entries."
                  ::= { readEnhancedEventLogEntry 1 }

      readEnhancedEventLogAttribute OBJECT-TYPE
                  SYNTAX  OCTET STRING
                  MAX-ACCESS  read-only
                  STATUS  current -- was mandatory
                  DESCRIPTION
                  "A string of data detailing an event log's attribute, such as the 
                  Event ID and Call Home Flag. The Event ID is a hexadecimal number representing an specific or class of events. 
                  The call home flag indicates that the corresponding problem may result in a call home. 
                  For consistent results, view as a table and not as individual entries."
                  ::= { readEnhancedEventLogEntry 2}
         readEnhancedEventLogMessage OBJECT-TYPE
                  SYNTAX  OCTET STRING
                  MAX-ACCESS  read-only
                  STATUS  current -- was mandatory
                  DESCRIPTION
                  "A string of data detailing an event log message. 
                   For consistent results, view as a table and not as individual entries."
                  ::= { readEnhancedEventLogEntry 3}

     readAuditLogTable  OBJECT-TYPE
                    SYNTAX  SEQUENCE OF ReadAuditLogEntry
                    MAX-ACCESS  not-accessible
                    STATUS  current -- was mandatory
                    DESCRIPTION
                    "Table of audit log entry information. Audit log includes the logs whose source is 'Audit'"
                    ::= { eventLog 10 }

      readAuditLogEntry OBJECT-TYPE
                    SYNTAX ReadAuditLogEntry
                    MAX-ACCESS  not-accessible
                    STATUS  current -- was mandatory
                    DESCRIPTION
                    "Audit log table entry, new entries could be added for new items."
                    INDEX { readAuditLogNumber }
                    ::= { readAuditLogTable 1 }


      ReadAuditLogEntry ::= SEQUENCE {
                  readAuditLogNumber INTEGER,
                  readAuditLogAttribute OCTET STRING,
                  readAuditLogMessage OCTET STRING
                  }


      readAuditLogNumber  OBJECT-TYPE
                  SYNTAX  Integer32 (0..2147483647) -- was INTEGER
                  MAX-ACCESS  read-only
                  STATUS  current -- was mandatory
                  DESCRIPTION
                  "The audit log number.  
                  For consistent results, view as a table and not as individual entries."
                  ::= { readAuditLogEntry 1 }

      readAuditLogAttribute OBJECT-TYPE
                  SYNTAX  OCTET STRING
                  MAX-ACCESS  read-only
                  STATUS  current -- was mandatory
                  DESCRIPTION
                  "A string of data detailing an audit eventlog's attribute.  
                  For consistent results, view as a table and not as individual entries."
                  ::= { readAuditLogEntry 2 }
      readAuditLogMessage OBJECT-TYPE
                  SYNTAX  OCTET STRING
                  MAX-ACCESS  read-only
                  STATUS  current -- was mandatory
                  DESCRIPTION
                  "A string of data detailing an audit event log message.  
                  For consistent results, view as a table and not as individual entries."
                  ::= { readAuditLogEntry 3 }

     clearAuditLog OBJECT-TYPE
                  SYNTAX  INTEGER {
                    execute(1)
                  }
                  MAX-ACCESS  read-write
                  STATUS  current -- was mandatory
                  DESCRIPTION
                  "Clear the audit log. 
                  
                  NOTE: Value returned for the GET command is meaningless for this 
                  MIB object."
                  ::= { eventLog 11 }

     readSystemLogTable  OBJECT-TYPE
                    SYNTAX  SEQUENCE OF ReadSystemLogEntry
                    MAX-ACCESS  not-accessible
                    STATUS  current -- was mandatory
                    DESCRIPTION
                    "Table of system log entry information. System log includes the logs whose source is other than 'Audit'"
                    ::= { eventLog 12 }

      readSystemLogEntry OBJECT-TYPE
                    SYNTAX ReadSystemLogEntry
                    MAX-ACCESS  not-accessible
                    STATUS  current -- was mandatory
                    DESCRIPTION
                    "System log table entry, new entries could be added for new items."
                    INDEX { readSystemLogNumber }
                    ::= { readSystemLogTable 1 }


      ReadSystemLogEntry ::= SEQUENCE {
                  readSystemLogNumber INTEGER,
                  readSystemLogAttribute OCTET STRING,
                  readSystemLogMessage OCTET STRING
                  }


      readSystemLogNumber  OBJECT-TYPE
                  SYNTAX  Integer32 (0..2147483647) -- was INTEGER
                  MAX-ACCESS  read-only
                  STATUS  current -- was mandatory
                  DESCRIPTION
                  "The system log index number.  
                  For consistent results, view as a table and not as individual entries."
                  ::= { readSystemLogEntry 1 }

      readSystemLogAttribute OBJECT-TYPE
                  SYNTAX  OCTET STRING
                  MAX-ACCESS  read-only
                  STATUS  current -- was mandatory
                  DESCRIPTION
                  "A string of data detailing an system event log's attribute.  
                  For consistent results, view as a table and not as individual entries."
                  ::= { readSystemLogEntry 2 }
        readSystemLogMessage OBJECT-TYPE
                  SYNTAX  OCTET STRING
                  MAX-ACCESS  read-only
                  STATUS  current -- was mandatory
                  DESCRIPTION
                  "A string of data detailing an system event log message.  
                  For consistent results, view as a table and not as individual entries."
                  ::= { readSystemLogEntry 3 }

     clearSystemLog OBJECT-TYPE
                  SYNTAX  INTEGER {
                    execute(1)
                  }
                  MAX-ACCESS  read-write
                  STATUS  current -- was mandatory
                  DESCRIPTION
                  "Clear the system log. 
                  
                  NOTE: Value returned for the GET command is meaningless for this 
                  MIB object."
                  ::= { eventLog 13 }

    
--  ********************************************************************************
--  Configure the MM
--  ********************************************************************************
    -- ********************************************************************************
    -- Remote Access Configuration
    -- ********************************************************************************
    remoteAccessConfig  OBJECT IDENTIFIER ::= { configureSP 1 }

     -- ********************************************************************************
     -- General Remote Access and Remote Alerts Configuration
     -- ********************************************************************************
     generalRemoteCfg    OBJECT IDENTIFIER ::= { remoteAccessConfig 1 }

      remoteAlertRetryDelay OBJECT-TYPE
                   SYNTAX  INTEGER {
                     noDelay(0),                   -- deprecated
                     oneHalfMinute(30),
                     oneMinute(60),
                     oneAndHalfMinutes(90),
                     twoMinutes(120),
                     twoAndHalfMinutes(150),
                     threeMinutes(180),
                     threeAndHalfMinutes(210),
                     fourMinutes(240)
                   }
                   MAX-ACCESS  read-write
                   STATUS  current -- was mandatory
                   DESCRIPTION
                   "Number in seconds to delay between retries if sending a
                   remote alert is unsuccessful."
                   ::= { generalRemoteCfg 3 }
                   
      remoteAlertRetryCount OBJECT-TYPE
                   SYNTAX  INTEGER {
                     noretry(0),
                     retry1(1),
                     retry2(2),
                     retry3(3),
                     retry4(4),
                     retry5(5),
                     retry6(6),
                     retry7(7),
                     retry8(8)
                   }
                   MAX-ACCESS  read-write
                   STATUS  current -- was mandatory
                   DESCRIPTION
                   "Number of additional times a remote alert will be
                   retried if not successfully sent. A value of zero indicates
                   no retries will be attempted."
                   ::= { generalRemoteCfg 4 }

      remoteAlertEntryDelay OBJECT-TYPE
                   SYNTAX  INTEGER {
                     noDelay(0),
                     oneHalfMinute(30),
                     oneMinute(60),
                     oneAndHalfMinutes(90),
                     twoMinutes(120),
                     twoAndHalfMinutes(150),
                     threeMinutes(180),
                     threeAndHalfMinutes(210),
                     fourMinutes(240)
                   }
                   MAX-ACCESS  read-only
                   STATUS  deprecated
                   DESCRIPTION
                   "Number in seconds to delay between entries if sending a
                   remote alert is unsuccessful.

                   NOTE: This object is no longer supported. However, for
                   compatibilities sake, a value of (255) is returned when
                   read. Also, write access has been removed."
                   ::= { generalRemoteCfg 5 }

      remoteAccessTamperDelay OBJECT-TYPE
                   SYNTAX  INTEGER {
                     nowait(0),
                     oneMinute(1),
                     twoMinutes(2),
                     threeMinutes(3),
                     fourMinutes(4),
                     fiveMinutes(5),
                     sixMinutes(6),
                     sevenMinutes(7),
                     tenMinutes(10),
                     fifteenMinutes(15),
                     twentyMinutes(20),
                     thirtyMinutes(30),
                     sixtyMinutes(60),
                     oneTwentyMinutes(120),
                     oneEightyMinutes(180),
                     twoFortyMinutes(240)
                   }
                   MAX-ACCESS  read-write
                   STATUS  deprecated
                   DESCRIPTION
                   "This value is no longer supported and has been replaced by
                   'lockoutPeriod'."
                   ::= { generalRemoteCfg 6 }


      userAuthenticationMethod OBJECT-TYPE
                    SYNTAX  INTEGER {
                       localOnly(0),
                       ldapOnly(1),
                       localFirstThenLdap(2),
                       ldapFirstThenLocal(3)
                    }
                    MAX-ACCESS  read-write
                    STATUS  current -- was mandatory
                    DESCRIPTION
                    "Use this field to specify how users attempting to login should be authenticated. 
                    There are two methods: 
                       Local authentication. Userid and password are verified by searching the list 
                          of users locally configured under Local Login Profiles.
                       LDAP based authentication. Users are authenticated via a remote LDAP server.
                    One or both authentication methods can be selected. If both methods should be 
                    used, the order must be specified."
                    ::= { generalRemoteCfg 7 }

      maxSessionsPerLDAPUser OBJECT-TYPE
                    SYNTAX INTEGER
                    MAX-ACCESS read-write
                    STATUS current -- was mandatory
                    DESCRIPTION
                    "The maximum number of simultaneous active sessions allowed for
                    each LDAP user. If the value is 0, this option is disabled. The
                    minimum value is 1 and the maximum value is 20."
                    ::= { generalRemoteCfg 9 }
      authenticationLoggingTimeout  OBJECT-TYPE
                    SYNTAX  INTEGER {
                         logAll(0),
                         fiveSeconds(1),
                         thirtySeconds(2),
                         oneMinute(3),
                         fiveMinutes(4),
                         tenMinutes(5),
                         thirtyMinutes(6),
                         oneHour(7),
                         twelveHours(8),
                         oneDay(9),
                         logNone(255)
                   }
                    MAX-ACCESS read-write
                    STATUS current -- was mandatory
                    DESCRIPTION
                    "Use this option to set how long, in seconds, AMM will not log the authentication
                    events for the same user. The default setting is 5 minutes. 0 indicates log all 
                    authentication events, 255 indicates don't log any new authentication events."
                   ::= { generalRemoteCfg 10 }
      trackingIP    OBJECT-TYPE
                    SYNTAX INTEGER {
                          disable(0),
                          enable(1)                        
                    }
                    MAX-ACCESS read-write
                    STATUS current -- was mandatory
                    DESCRIPTION
                    "This option indicates tracking different IP addresses for the same user is 
                    enabled or not. If it is enabled then an access every second from 
                    alternating IP addresses will result in multiple log entries, 
                    regardless of the time duration set in the 'authenticaionLoggingTimeout'field.
                    If this flag is disabled, multiple accesses by varying IP addresses 
                    will only be logged as 'new' accesses if they are out of the 
                    'authenticationLoggingTimeout'."
                    ::= { generalRemoteCfg 11 }
              
    -- ********************************************************************************
    -- Account security management
    -- ********************************************************************************
     accountSecurityManagement OBJECT IDENTIFIER ::= { generalRemoteCfg 20 }

      accountSecurityLevel OBJECT-TYPE
                   SYNTAX  INTEGER {
                     legacy(0),
                     high(1),
                     custom(2)
                   }
                   MAX-ACCESS  read-write
                   STATUS  current -- was mandatory
                   DESCRIPTION
                   "The level of security needed for local user login passwords.
                        The legacy level:
                            - no password required
                            - no password expiration
                            - no password re-use restrictions
                            - no frequency of password change restrictions
                            - account is locked for 2 minutes after 5 login failures
                            - simple password rules
                            - no account inactivity monitoring
                        The high level:
                            - password required
                            - factory default 'USERID' account password must be changed on next login
                            - force user to change password on first login
                            - password expires in 90 days
                            - password re-use checking enabled (last 5 passwords kept in history)
                            - minimum 24 hours interval between password changes
                            - account is locked for 60 minutes after 5 login failures
                            - complex password rules with 2 degrees of difference from previous password
                            - alert on account inactivity after 120 days
                            - accounts disabled after 180 days of inactivity
                        The custom level:
                            - set the password settings individually under customSecuritySettings
                   The default value is legacy."
                   ::= { accountSecurityManagement 1 }


     customSecuritySettings OBJECT IDENTIFIER ::= { accountSecurityManagement 2 }

      loginPasswordRequired OBJECT-TYPE
                   SYNTAX  INTEGER {
                     disabled(0),
                     enabled(1)
                   }
                   MAX-ACCESS  read-write
                   STATUS  current -- was mandatory
                   DESCRIPTION
                   "If enabled, all users require a login password to access the AMM.
                   If disabled, empty password is allowed and complex password rules 
                   will be disabled automatically.
                   The default value is disabled."
                   ::= { customSecuritySettings 1 }

      passwordExpirationPeriod OBJECT-TYPE
                   SYNTAX  INTEGER
                   MAX-ACCESS  read-write
                   STATUS  current -- was mandatory
                   DESCRIPTION
                   "The number of days before login passwords expire.  The minimum 
                   value is 1 day and the maximum value is 365 days.  The default 
                   value is 90 days.  A value of 0 disables this option."
                   ::= { customSecuritySettings 2 }

      defaultAdminPasswordExpired OBJECT-TYPE
                   SYNTAX  INTEGER {
                     disabled(0),
                     enabled(1)
                   }
                   MAX-ACCESS  read-write
                   STATUS  current -- was mandatory
                   DESCRIPTION
                   "If enabled, the factory default 'USERID' account password must 
                   be changed on next login.  The default value is disabled."
                   ::= { customSecuritySettings 3 }

      minimumPasswordReuseCycle OBJECT-TYPE
                   SYNTAX  INTEGER {
                     none(0),
                     onePassword(1),
                     twoPasswords(2),
                     threePasswords(3),
                     fourPasswords(4),
                     fivePasswords(5)
                   }
                   MAX-ACCESS  read-write
                   STATUS  current -- was mandatory
                   DESCRIPTION
                   "The number of unique passwords a user must choose before
                   reusing a password.  The default value is none."
                   ::= { customSecuritySettings 4 }

      complexPasswordRules OBJECT-TYPE
                   SYNTAX  INTEGER {
                     disabled(0),
                     enabled(1)
                   }
                   MAX-ACCESS  read-write
                   STATUS  current -- was mandatory
                   DESCRIPTION
                   "If enabled, the minimum complexity rules will be enforced for all
                   local login passwords and 'User login password required' rule will be enabled.
                   The rules are as follows:
                        Passwords must be a minimum of eight characters.
                        Passwords must not be a repeat or reverse of the associated login id.
                        Passwords must be no more than three of the same characters used consecutively.
                        Passwords must contain at least three of the following combinations:
                            At least one lower case alphanumeric character.
                            At least one upper case alphanumeric character.
                            At least one numeric character.
                            At least one special character.
                   The default value is disabled."
                   ::= { customSecuritySettings 5 }

      minimumDiffCharsPassword OBJECT-TYPE
                   SYNTAX  INTEGER {
                     none(0),
                     oneChar(1),
                     twoChars(2),
                     threeChars(3),
                     fourChars(4),
                     fiveChars(5),
                     sixChars(6),
                     sevenChars(7),
                     eightChars(8),
                     nineChars(9),
                     tenChars(10),
                     elevenChars(11),
                     twelveChars(12),
                     thirteenChars(13),
                     fourteenChars(14),
                     fifteenChars(15)
                   }
                   MAX-ACCESS  read-write
                   STATUS  current -- was mandatory
                   DESCRIPTION
                   "The required minimum number of characters in the new password 
                   different from the previous password.  The default value is 2."
                   ::= { customSecuritySettings 6 }

      changePasswordFirstAccess OBJECT-TYPE
                   SYNTAX  INTEGER {
                     disabled(0),
                     enabled(1)
                   }
                   MAX-ACCESS  read-write
                   STATUS  current -- was mandatory
                   DESCRIPTION
                   "If enabled, the login user will be forced to change their password on
                   the first access after the account has been established or on
                   the first access after an administrator has changed the password 
                   for the user, except for the administrator password for USERID.
                   The default value is disabled."
                   ::= { customSecuritySettings 7 }

      inactivityAlertPeriod OBJECT-TYPE
                   SYNTAX  INTEGER
                   MAX-ACCESS  read-write
                   STATUS  current -- was mandatory
                   DESCRIPTION
                   "The period of time in days before generating an alert for a dormant
                   account. This value applies to all login accounts, including the 
                   administrator account.  The minimum value is 1 day and the maximum
                   value is 365 days.  The default value is 0 which disables this option.
                   NOTE: This value must be less than the inactivityAlertDisablePeriod."
                   ::= { customSecuritySettings 8 }

      inactivityAlertDisablePeriod OBJECT-TYPE
                   SYNTAX  INTEGER
                   MAX-ACCESS  read-write
                   STATUS  current -- was mandatory
                   DESCRIPTION
                   "The period of time in days before generating an alert and disabling
                   a dormant account. This value applies to all login accounts, excluding 
                   the administrator account.  The minimum value is 1 day and the maximum
                   value is 365 days.  The default value is 0 which disables this option.
                   NOTE: This value must be greater than the inactivityAlertPeriod."
                   ::= { customSecuritySettings 9 }

      lockoutPeriod OBJECT-TYPE
                   SYNTAX  INTEGER
                   MAX-ACCESS  read-write
                   STATUS  current -- was mandatory
                   DESCRIPTION
                   "The period of time in minutes that a user is locked out after the
                   maximum number of login failures was reached.  The minimum value is 
                   is 1 minute and the maximum value is 2880 minutes.  The default value
                   is 2 minutes for the Legacy security level and 60 minutes for the
                   High security level.  A value of 0 disables this option."
                   ::= { customSecuritySettings 10 }

      maxLoginFailures OBJECT-TYPE
                   SYNTAX  INTEGER {
                     none(0),
                     oneTime(1),
                     twoTimes(2),
                     threeTimes(3),
                     fourTimes(4),
                     fiveTimes(5),
                     sixTimes(6),
                     sevenTimes(7),
                     eightTimes(8),
                     nineTimes(9),
                     tenTimes(10)
                   }
                   MAX-ACCESS  read-write
                   STATUS  current -- was mandatory
                   DESCRIPTION
                   "The maximum number of login failures before a user account is locked.
                   A value of 0 disables this option.  The default value is 5."
                   ::= { customSecuritySettings 11 }

      passwordChangeInterval OBJECT-TYPE
                   SYNTAX  INTEGER
                   MAX-ACCESS  read-write
                   STATUS  current -- was mandatory
                   DESCRIPTION
                   "A minimum period of time that user is not able to change
                   their own password. The range of acceptable values will be 
                   from 0 to 1440 (or 60 days). A value of 0 disables this 
                   option. If the password expiration period is set, it must be
                   greater than the minimum password change interval."
                   ::= { customSecuritySettings 12 }

     -- ***********************************************************************
     -- Serial Port Configuration
     -- ***********************************************************************
     serialPortCfg  OBJECT IDENTIFIER ::= { remoteAccessConfig 2 }

       portBaud     OBJECT-TYPE
                    SYNTAX  INTEGER {
                      baud2400(0),
                      baud4800(1),
                      baud9600(3),
                      baud19200(7),
                      baud38400(15),
                      baud57600(23)
                    }
                    MAX-ACCESS  read-write
                    STATUS  current -- was mandatory
                    DESCRIPTION
                    "Baud rate for the serial port."
                    ::= { serialPortCfg 1 }

       portParity   OBJECT-TYPE
                    SYNTAX  INTEGER {
                      none(0),
                      odd(1),
                      even(3),
                      mark(5),
                      space(7)
                    }
                    MAX-ACCESS  read-write
                    STATUS  current -- was mandatory
                    DESCRIPTION
                    "Parity setting for the serial port."
                    ::= { serialPortCfg 2 }

       portStopBits OBJECT-TYPE
                    SYNTAX  INTEGER {
                      oneStopbit(0),
                      twoOrOnePtFive(1)
                    }
                    MAX-ACCESS  read-write
                    STATUS  current -- was mandatory
                    DESCRIPTION
                    "Number of stop bits for the serial port."
                    ::= { serialPortCfg 3 }


     -- ********************************************************************************
     -- Remote Alert Profiles
     -- ********************************************************************************
     remoteAlertIds OBJECT IDENTIFIER ::= { remoteAccessConfig 3 }

      remoteAlertIdsTable   OBJECT-TYPE
                            SYNTAX  SEQUENCE OF RemoteAlertIdsEntry
                            MAX-ACCESS  not-accessible
                            STATUS  current -- was mandatory
                            DESCRIPTION
                            "Table of remote alert entries.
                            This table lets you configure remote alert recipients.
                            You can define up to 12 unique recipients.
                            NOTE: All selected alert events will be sent to all
                            enabled alert recipients."
                            ::= {  remoteAlertIds 1 }

      remoteAlertIdsEntry   OBJECT-TYPE
                            SYNTAX RemoteAlertIdsEntry
                            MAX-ACCESS  not-accessible
                            STATUS  current -- was mandatory
                            DESCRIPTION
                            "Remote alert entries."
                            INDEX { remoteAlertIdEntryIndex }
                            ::= { remoteAlertIdsTable 1 }


      RemoteAlertIdsEntry ::= SEQUENCE {
                   remoteAlertIdEntryIndex INTEGER,
                   remoteAlertIdEntryStatus INTEGER,
                   remoteAlertIdEntryIpOrHostAddress OCTET STRING,
                   remoteAlertIdEntryTextDescription OCTET STRING,
                   remoteAlertIdEntryNotificationType INTEGER,
                   remoteAlertIdEmailAddr OCTET STRING,
                   remoteAlertIdEntrySelectiveAlert INTEGER
                   }


      remoteAlertIdEntryIndex   OBJECT-TYPE
                                SYNTAX  Integer32 (0..2147483647) -- was INTEGER
                                MAX-ACCESS  read-only
                                STATUS  current -- was mandatory
                                DESCRIPTION
                                "Index for remote alert entry."
                                ::= { remoteAlertIdsEntry 1 }

      remoteAlertIdEntryStatus  OBJECT-TYPE
                                SYNTAX  INTEGER {
                                  invalid(0),
                                  disabledAndValid(1),
                                  enabledAndValid(2)
                                }
                                MAX-ACCESS  read-write
                                STATUS  current -- was mandatory
                                DESCRIPTION
                                "Remote alert entry status, invalid means entry
                                not defined yet, disabledAndValid means entry defined
                                but not enabled to send an alert, enabledAndValid means
                                entry defined and enabled to send an alert."
                                ::= { remoteAlertIdsEntry 2 }

      remoteAlertIdEntryIpOrHostAddress OBJECT-TYPE
                                SYNTAX  OCTET STRING (SIZE(0..50))
                                MAX-ACCESS  read-write
                                STATUS  current -- was mandatory
                                DESCRIPTION
                                "A null terminated string that either
                                contains an IP address of the form '1.2.3.4'
                                or a host name (if DNS is enabled) for the
                                alert entry."
                                ::= { remoteAlertIdsEntry 3 }

      remoteAlertIdEntryTextDescription  OBJECT-TYPE
                                SYNTAX  OCTET STRING (SIZE(0..50))
                                MAX-ACCESS  read-write
                                STATUS  current -- was mandatory
                                DESCRIPTION
                                "A null terminated string that contains
                                a text description of this entry."
                                ::= { remoteAlertIdsEntry 4 }

      remoteAlertIdEntryNotificationType OBJECT-TYPE
                                SYNTAX  INTEGER {
                                  unknown(0),
                                  ibmDirectorOverLAN(8),
                                  snmpOverLan(4),
                                  emailOverLan(5)
                                }
                                MAX-ACCESS  read-write
                                STATUS  current -- was mandatory
                                DESCRIPTION
                                "Remote alert entry notification method.  Types include
                                unknown when the type can't be determined (read-only),
                                ibmDirectorOverLAN for a LAN alert sent over ethernet to
                                IBM director, snmpOverLan for an SNMP alert over ethernet,
                                and emailOverLan for a E-Mail alert over ethernet."
                                ::= { remoteAlertIdsEntry 5 }

      remoteAlertIdEmailAddr    OBJECT-TYPE
                                SYNTAX  OCTET STRING(SIZE(0..64))
                                MAX-ACCESS  read-write
                                STATUS  current -- was mandatory
                                DESCRIPTION
                                "A null terminated string that contains an
                                E-Mail Address.  For example, 'jeb@us.ibm.com'.
                                Used only for an E-mail over LAN or E-Mail over PPP
                                notification type."
                                ::= { remoteAlertIdsEntry 9 }

      remoteAlertIdEntrySelectiveAlert OBJECT-TYPE
                                SYNTAX  INTEGER {
                                  critOnlyAlerts(0),
                                  allAlerts(1)
                                }
                                MAX-ACCESS  read-write
                                STATUS  current -- was mandatory
                                DESCRIPTION
                                "Remote alert entry selective alert setting.  A value of
                                critOnlyAlerts will only send critical alerts to this
                                remote alert recipient, a value of allAlerts will send
                                all alerts to this remote alert recipient."
                                ::= { remoteAlertIdsEntry 13 }

      generateTestAlert  OBJECT-TYPE
                   SYNTAX  INTEGER {
                    execute(1)
                   }
                   MAX-ACCESS  read-write
                   STATUS  current -- was mandatory
                   DESCRIPTION
                   "Generate a Test Alert.  This will send a test alert to all configured
                   and enabled remote alert recipients. The text portion of the alert
                   will contain 'Application Posted Alert to MM'.
                   
                   NOTE: Value returned for the GET command is meaningless for this 
                   MIB object.

                         If user enables Automated FTP/TFTP report of service data, 
                   report of service data via FTP/TFTP on the test alert will be made. 
                   User can also validate the configurations of Automated FTP/TFTP Report 
                   of service data."
                   ::= { remoteAlertIds 30 }

     -- ********************************************************************************
     -- Remote Access Profiles
     -- ********************************************************************************
     remoteAccessIds OBJECT IDENTIFIER ::= { remoteAccessConfig 4 }

      remoteAccessIdsTable  OBJECT-TYPE
                            SYNTAX  SEQUENCE OF RemoteAccessIdsEntry
                            MAX-ACCESS  not-accessible
                            STATUS  current -- was mandatory
                            DESCRIPTION
                            "Table of remote access profiles.

                            This table lets you to configure all login profiles.
                            You can define up to 12 unique profiles.

                            NOTE: By default, the management module
                            comes configured with one login profile that allows remote
                            access using a login ID of 'USERID' and a password of 'PASSW0RD'
                            (the 0 is a zero).  To avoid a potential security exposure,
                            we strongly recommend that you change this default Login
                            Profile to values of your choice."
                            ::= {  remoteAccessIds 1 }

      remoteAccessIdsEntry  OBJECT-TYPE
                            SYNTAX RemoteAccessIdsEntry
                            MAX-ACCESS  not-accessible
                            STATUS  current -- was mandatory
                            DESCRIPTION
                            "Remote access entries."
                            INDEX { remoteAccessIdEntryIndex }
                            ::= { remoteAccessIdsTable 1 }


      RemoteAccessIdsEntry ::= SEQUENCE {
                   remoteAccessIdEntryIndex INTEGER,
                   remoteAccessIdEntryUserId OCTET STRING,
                   remoteAccessIdEntryPassword OCTET STRING,
                   remoteAccessIdEntryEncodedLoginPw OCTET STRING,
                   remoteAccessIdEntryRole OCTET STRING,
                   remoteAccessIdEntryLoggedIn INTEGER,
                   remoteAccessIdEntryLastLogin OCTET STRING,
                   remoteAccessIdEntryPwdCompliant INTEGER,
                   remoteAccessIdEntryPwdExp OCTET STRING,
                   remoteAccessIdEntryDormant INTEGER,
                   remoteAccessIdEntryState INTEGER,
                   remoteAccessIdEntryAction INTEGER,
                   remoteAccessIdEntrySessionCount INTEGER,
                   remoteAccessIdEntryMaxSessions INTEGER
                   }


      remoteAccessIdEntryIndex  OBJECT-TYPE
                                SYNTAX  INTEGER(0..255)
                                MAX-ACCESS  read-only
                                STATUS  current -- was mandatory
                                DESCRIPTION
                                "Index for Remote access entry."
                                ::= { remoteAccessIdsEntry 1 }

      remoteAccessIdEntryUserId    OBJECT-TYPE
                                SYNTAX  OCTET STRING (SIZE(0..16))
                                MAX-ACCESS  read-write
                                STATUS  current -- was mandatory
                                DESCRIPTION
                                "Remote access entry null terminated string that
                                contains the user-id.  It must not be a duplicate of 
                                any previously configured ones."
                                ::= { remoteAccessIdsEntry 2 }

      remoteAccessIdEntryPassword OBJECT-TYPE
                                SYNTAX  OCTET STRING (SIZE(0..16))
                                MAX-ACCESS  read-write
                                STATUS  current -- was mandatory
                                DESCRIPTION
                                "Remote access password.  The password must
                                contain at least one alphabetic and one
                                non-alphabetic character and be at least 5
                                characters long, or you can leave the password
                                field blank to set an empty password.
                                
                                NOTE: Value returned by the GET command is meaningless
                                for this MIB object."
                                ::= { remoteAccessIdsEntry 3 }

      remoteAccessIdEntryEncodedLoginPw OBJECT-TYPE
                                SYNTAX  OCTET STRING (SIZE(0..36))
                                MAX-ACCESS  read-write
                                STATUS  current -- was mandatory
                                DESCRIPTION
                                "Used only for configuration save/restore.
                                A null terminated string containing an encoded
                                concatenation of the login ID and password
                                separated by an ':'."
                                ::= { remoteAccessIdsEntry 7 }

      remoteAccessIdEntryRole   OBJECT-TYPE
                                SYNTAX  OCTET STRING
                                MAX-ACCESS  read-only
                                STATUS  current -- was mandatory
                                DESCRIPTION
                                "Indicates if user has supervisor, operator, or custom access."
                                ::= { remoteAccessIdsEntry 10 }

      remoteAccessIdEntryLoggedIn OBJECT-TYPE
                                SYNTAX  INTEGER {
                                    no(0),
                                    yes(1)
                                }
                                MAX-ACCESS  read-only
                                STATUS  current -- was mandatory
                                DESCRIPTION
                                "Indicates if user is currently logged in or not."
                                ::= { remoteAccessIdsEntry 11 }

      remoteAccessIdEntryLastLogin OBJECT-TYPE
                                SYNTAX  OCTET STRING
                                MAX-ACCESS  read-only
                                STATUS  current -- was mandatory
                                DESCRIPTION
                                "Timestamp for the last successful login by the user."
                                ::= { remoteAccessIdsEntry 12 }

      remoteAccessIdEntryPwdCompliant OBJECT-TYPE
                                SYNTAX  INTEGER {
                                    no(0),
                                    yes(1)
                                }
                                MAX-ACCESS  read-only
                                STATUS  current -- was mandatory
                                DESCRIPTION
                                "Indicates if user complies with all of the password
                                rules currently in effect."
                                ::= { remoteAccessIdsEntry 13 }

      remoteAccessIdEntryPwdExp OBJECT-TYPE
                                SYNTAX  OCTET STRING
                                MAX-ACCESS  read-only
                                STATUS  current -- was mandatory
                                DESCRIPTION
                                "The number of days until the user's current password expires."
                                ::= { remoteAccessIdsEntry 14 }

      remoteAccessIdEntryDormant  OBJECT-TYPE
                                SYNTAX  INTEGER {
                                    no(0),
                                    yes(1)
                                }
                                MAX-ACCESS  read-only
                                STATUS  current -- was mandatory
                                DESCRIPTION
                                "Indicates if the user account has been inactive for a 
                                specified amount of time based on inactivityAlertDisablePeriod
                                in the customSecuritySettings section."
                                ::= { remoteAccessIdsEntry 15 }

      remoteAccessIdEntryState  OBJECT-TYPE
                                SYNTAX  INTEGER {
                                   disabled(0),
                                   active(1),
                                   locked(2)
                                }
                                MAX-ACCESS  read-only
                                STATUS  current -- was mandatory
                                DESCRIPTION
                                "Indicates the state of the user:
                                  Active - normal state
                                  Disabled - user cannot use account until enabled by a
                                    supervisor or chassis user account manager.  An account
                                    can get disabled after being dormant for a specified
                                    amount of time OR as a result of a supervisor or chassis
                                    user account manager disabling it.  
                                  Locked - account is temporarily locked due to repeated
                                    unsuccessful login attempts as specified by lockoutPeriod
                                    in the customSecuritySettings section.  Account can be
                                    unlocked by a supervisor or chassis user account manager
                                    OR can be automatically unlocked after the lockoutPeriod expires.

                                NOTE: The disable action does not apply to supervisor or chassis
                                    user account manager accounts."
                                ::= { remoteAccessIdsEntry 16 }

      remoteAccessIdEntryAction OBJECT-TYPE
                                SYNTAX  INTEGER {
                                    disable(0),
                                    enable(1),
                                    unlock(2),
                                    notApplicable(255)
                                }
                                MAX-ACCESS  read-write
                                STATUS  current -- was mandatory
                                DESCRIPTION
                                "Actions that only a supervisor or chassis user account manager 
                                can perform for each user id:
                                  Enable - enables an account in the Disabled state
                                  Disable - disables an account in the Active or Locked state
                                  Unlock - unlock an account in the Locked state

                                NOTE: The disable action does not apply to supervisor or chassis
                                    user account manager accounts.

                                NOTE: Value returned for the GET command is meaningless for this 
                                    MIB object."
                                ::= { remoteAccessIdsEntry 17 }

      remoteAccessIdEntrySessionCount OBJECT-TYPE
                                      SYNTAX INTEGER
                                      MAX-ACCESS read-only
                                      STATUS current -- was mandatory
                                      DESCRIPTION
                                      "The number of sessions the user is currently logged in to."
                                      ::= { remoteAccessIdsEntry 18 }

      remoteAccessIdEntryMaxSessions OBJECT-TYPE
                                     SYNTAX INTEGER
                                     MAX-ACCESS read-write
                                     STATUS current -- was mandatory
                                     DESCRIPTION
                                     "The maximum number of simultaneous active sessions allowed for
                                     the user. If the value is 0, this option is disabled. The
                                     minimum value is 1 and the maximum value is 20."
                                     ::= { remoteAccessIdsEntry 19 }

    -- ********************************************************************************

      remoteAccessUserAuthorityLevelTable  OBJECT-TYPE
                            SYNTAX  SEQUENCE OF RemoteAccessUserAuthorityLevelEntry
                            MAX-ACCESS  not-accessible
                            STATUS  current -- was mandatory
                            DESCRIPTION
                            "Table of user authority level profiles."
                            ::= {  remoteAccessIds 2 }
                            
      remoteAccessUserAuthorityLevelEntry  OBJECT-TYPE
                            SYNTAX RemoteAccessUserAuthorityLevelEntry
                            MAX-ACCESS  not-accessible
                            STATUS  current -- was mandatory
                            DESCRIPTION
                            "User authority level entries."
                            INDEX { ualIndex }
                            ::= { remoteAccessUserAuthorityLevelTable 1 }
                            
      RemoteAccessUserAuthorityLevelEntry ::= SEQUENCE { 
                   ualIndex INTEGER,
                   ualId OCTET STRING,
                   ualSupervisor INTEGER,
                   ualReadOnly INTEGER,
                   ualAccountManagement INTEGER,
                   ualConsoleAccess INTEGER,
                   ualConsoleAndVirtualMediaAccess INTEGER,
                   ualServerPowerAccess INTEGER,
                   ualAllowClearLog INTEGER,
                   ualAdapterBasicConfig INTEGER,
                   ualAdapterNetworkAndSecurityConfig INTEGER,
                   ualAdapterAdvancedConfig INTEGER
                   }
      
      ualIndex  OBJECT-TYPE
                    SYNTAX  INTEGER(0..255) 
                    MAX-ACCESS  read-only
                    STATUS  current -- was mandatory
                    DESCRIPTION
                    "Index for User Authority Level entry."  
                    ::= { remoteAccessUserAuthorityLevelEntry 1 }

      ualId    OBJECT-TYPE
                    SYNTAX  OCTET STRING (SIZE(0..16))
                    MAX-ACCESS  read-only
                    STATUS  current -- was mandatory
                    DESCRIPTION
                    "User ID"
                    ::= { remoteAccessUserAuthorityLevelEntry 2 }

      ualSupervisor OBJECT-TYPE
                    SYNTAX  INTEGER {
                       disabled(0),
                       enabled(1)
                    }
                    MAX-ACCESS  read-write
                    STATUS  current -- was mandatory
                    DESCRIPTION
                    "User has no restrictions."
                    ::= { remoteAccessUserAuthorityLevelEntry 3 }

      ualReadOnly OBJECT-TYPE
                    SYNTAX  INTEGER {
                       disabled(0),
                       enabled(1)
                    }
                    MAX-ACCESS  read-write
                    STATUS  current -- was mandatory
                    DESCRIPTION
                    "User has only read-only access, and cannot perform any save, modify, 
                    clear, or state affecting operations (e.g. restart MM, restore defaults, 
                    upgrade the firmware, etc.)."
                    ::= { remoteAccessUserAuthorityLevelEntry 4 }

      ualAccountManagement OBJECT-TYPE
                    SYNTAX  INTEGER {
                       disabled(0),
                       enabled(1)
                    }
                    MAX-ACCESS  read-write
                    STATUS  current -- was mandatory
                    DESCRIPTION
                    "User can add/modify/delete users and change the global login settings in 
                    the Login Profiles panel."
                    ::= { remoteAccessUserAuthorityLevelEntry 5 }

      ualConsoleAccess OBJECT-TYPE
                    SYNTAX  INTEGER {
                       disabled(0),
                       enabled(1)
                    }
                    MAX-ACCESS  read-write
                    STATUS  current -- was mandatory
                    DESCRIPTION
                    "User can access the remote console."
                    ::= { remoteAccessUserAuthorityLevelEntry 6 }

      ualConsoleAndVirtualMediaAccess OBJECT-TYPE
                    SYNTAX  INTEGER {
                       disabled(0),
                       enabled(1)
                    }
                    MAX-ACCESS  read-write
                    STATUS  current -- was mandatory
                    DESCRIPTION
                    "User can access both the remote console and the virtual media feature."
                    ::= { remoteAccessUserAuthorityLevelEntry 7 }

      ualServerPowerAccess OBJECT-TYPE
                    SYNTAX  INTEGER {
                       disabled(0),
                       enabled(1)
                    }
                    MAX-ACCESS  read-write
                    STATUS  current -- was mandatory
                    DESCRIPTION
                    "User can access the power on and restart functions for the remote server. 
                    These functions are available via the Power/Restart panel."
                    ::= { remoteAccessUserAuthorityLevelEntry 8 }

      ualAllowClearLog OBJECT-TYPE
                    SYNTAX  INTEGER {
                       disabled(0),
                       enabled(1)
                    }
                    MAX-ACCESS  read-write
                    STATUS  current -- was mandatory
                    DESCRIPTION
                    "User can clear the event logs. Everyone can look at the 
                    event logs, but this particular permission is required to clear the logs."
                    ::= { remoteAccessUserAuthorityLevelEntry 9 }
                    
      ualAdapterBasicConfig OBJECT-TYPE
                    SYNTAX  INTEGER {
                       disabled(0),
                       enabled(1)
                    }
                    MAX-ACCESS  read-write
                    STATUS  current -- was mandatory
                    DESCRIPTION
                    "User can modify configuration parameters in the System Settings and Alerts 
                    panels."
                    ::= { remoteAccessUserAuthorityLevelEntry 10 }
                    
      ualAdapterNetworkAndSecurityConfig OBJECT-TYPE
                    SYNTAX  INTEGER {
                       disabled(0),
                       enabled(1)
                    }
                    MAX-ACCESS  read-write
                    STATUS  current -- was mandatory
                    DESCRIPTION
                    "User can modify configuration parameters in the Security, Network Protocols, 
                    Network Interface, Port Assignments, and Serial Port panels."
                    ::= { remoteAccessUserAuthorityLevelEntry 11 }
                    
      ualAdapterAdvancedConfig OBJECT-TYPE
                    SYNTAX  INTEGER {
                       disabled(0),
                       enabled(1)
                    }
                    MAX-ACCESS  read-write
                    STATUS  current -- was mandatory
                    DESCRIPTION
                    "User has no restrictions when configuring the adapter. In addition, the 
                    user is said to have administrative access to the RSA, meaning that the 
                    user can also perform the following advanced functions: firmware upgrades, 
                    PXE network boot, restore adapter factory defaults, modify and restore 
                    adapter configuration from a configuration file, and restart/reset the 
                    adapter."
                    ::= { remoteAccessUserAuthorityLevelEntry 12 }
                    

      remoteAccessRBSroleTable  OBJECT-TYPE
                    SYNTAX  SEQUENCE OF RemoteAccessRBSroleEntry
                    MAX-ACCESS  not-accessible
                    STATUS  current -- was mandatory
                    DESCRIPTION
                    "Table of RBS User Role profiles."
                    ::= {  remoteAccessIds 3 }

      remoteAccessRBSroleEntry  OBJECT-TYPE
                    SYNTAX RemoteAccessRBSroleEntry
                    MAX-ACCESS  not-accessible
                    STATUS  current -- was mandatory
                    DESCRIPTION
                    "User Role entries."
                    INDEX { roleIndex }
                    ::= { remoteAccessRBSroleTable 1 }

      RemoteAccessRBSroleEntry ::= SEQUENCE {
                    roleIndex INTEGER,
                    roleId OCTET STRING,
                    rbsSupervisor INTEGER,
                    rbsOperator INTEGER,
                    rbsChassisOperator INTEGER,
                    rbsChassisAccountManagement INTEGER,
                    rbsChassisLogManagement INTEGER,
                    rbsChassisConfiguration INTEGER,
                    rbsChassisAdministration INTEGER,             
                    rbsBladeOperator INTEGER,
                    rbsBladeRemotePresence INTEGER,
                    rbsBladeConfiguration INTEGER,
                    rbsBladeAdministration INTEGER,
                    rbsSwitchModuleOperator INTEGER,
                    rbsSwitchModuleConfiguration INTEGER,
                    rbsSwitchModuleAdministration INTEGER,
                    rbsBladeRemotePresenseVideo INTEGER,       -- deprecated
                    rbsBladeRemotePresenseKVM INTEGER,         -- deprecated
                    rbsBladeRemotePresenseRdriveR INTEGER,     -- deprecated
                    rbsBladeRemotePresenseRdriveRW INTEGER,    -- deprecated
                    rbsChassisRemotePresenseRdoc INTEGER,      -- deprecated  
                    rbsRemotePresenceSupervisor INTEGER        -- deprecated
                    }


      roleIndex  OBJECT-TYPE
                    SYNTAX  INTEGER(0..255)
                    MAX-ACCESS  read-only
                    STATUS  current -- was mandatory
                    DESCRIPTION
                    "Index for RBS User Role entry."
                    ::= { remoteAccessRBSroleEntry 1 }

      roleId    OBJECT-TYPE
                    SYNTAX  OCTET STRING (SIZE(0..16))
                    MAX-ACCESS  read-only
                    STATUS  current -- was mandatory
                    DESCRIPTION
                    "User ID"
                    ::= { remoteAccessRBSroleEntry 2 }

      rbsSupervisor OBJECT-TYPE
                    SYNTAX  INTEGER {
                       disabled(0),
                       enabled(1)
                    }
                    MAX-ACCESS  read-write
                    STATUS  current -- was mandatory
                    DESCRIPTION
                    "User has no restrictions."
                    ::= { remoteAccessRBSroleEntry 3 }

      rbsOperator OBJECT-TYPE
                    SYNTAX  INTEGER {
                       disabled(0),
                       enabled(1)
                    }
                    MAX-ACCESS  read-write
                    STATUS  current -- was mandatory
                    DESCRIPTION
                    "User has read-only access, and cannot perform
                    any save, modify, clear, or state affecting operations
                    (e.g. restart MM, restore defaults, upgrade the firmware, etc.)."
                    ::= { remoteAccessRBSroleEntry 4 }

      rbsChassisOperator OBJECT-TYPE
                    SYNTAX  INTEGER {
                       disabled(0),
                       enabled(1)
                    }
                    MAX-ACCESS  read-write
                    STATUS  current -- was mandatory
                    DESCRIPTION
                    "User has ability to browse status and properties of
                    chassis components (MM, blowers (chassis cooling devices), midplane, power modules,
                    media tray. Ability to backup MM configuration to a file.
                    Saving MM configuration to chassis requires supervisor access."
                    ::= { remoteAccessRBSroleEntry 5 }


      rbsChassisAccountManagement OBJECT-TYPE
                    SYNTAX  INTEGER {
                       disabled(0),
                       enabled(1)
                    }
                    MAX-ACCESS  read-write
                    STATUS  current -- was mandatory
                    DESCRIPTION
                    "User can add/modify/delete user login profiles. Ability
                    to backup MM configuration to a file. Changing global login
                    settings require chassis configuration authority."
                    ::= { remoteAccessRBSroleEntry 6 }

      rbsChassisLogManagement OBJECT-TYPE
                    SYNTAX  INTEGER {
                       disabled(0),
                       enabled(1)
                    }             
                    MAX-ACCESS  read-write
                    STATUS  current -- was mandatory
                    DESCRIPTION
                    "User has ability to clear the MM event log, change log
                    policy settings, and backup MM configuration to a file."
                    ::= { remoteAccessRBSroleEntry 7 }

      rbsChassisConfiguration OBJECT-TYPE
                    SYNTAX  INTEGER {
                       disabled(0),
                       enabled(1)
                    }
                    MAX-ACCESS  read-write
                    STATUS  current -- was mandatory
                    DESCRIPTION
                    "User can modify and save any chassis configuration
                    parameter (except user profiles and event log settings). 
                    Ability to restore MM factory defaults if the user also has
                    chassis administration permissions. Ability to change the
                    global login settings, SOL configuration, and backup MM
                    configuration to a file."
                    ::= { remoteAccessRBSroleEntry 8 }

      rbsChassisAdministration OBJECT-TYPE
                    SYNTAX  INTEGER {
                       disabled(0),
                       enabled(1)
                    }
                    MAX-ACCESS  read-write
                    STATUS  current -- was mandatory
                    DESCRIPTION
                    "User has ability to do MM firmware updates, modify chassis
                    LEDs, restore MM factory defaults if the user also has 
                    chassis configuration permissions. Ability to restart MM 
                    and backup MM configuration to a file."
                    ::= { remoteAccessRBSroleEntry 9 }

      rbsBladeOperator OBJECT-TYPE
                    SYNTAX  INTEGER {
                       disabled(0),
                       enabled(1)
                    }
                    MAX-ACCESS  read-write
                    STATUS  current -- was mandatory
                    DESCRIPTION
                    "User has ability to browse status and properties of
                    blades."
                    ::= { remoteAccessRBSroleEntry 10 }

      rbsBladeRemotePresence OBJECT-TYPE
                    SYNTAX  INTEGER {
                       disabled(0),
                       enabled(1)
                    }
                    MAX-ACCESS  read-write
                    STATUS  current -- was mandatory
                    DESCRIPTION
                    "User has ability to access the Remote Control web panel
                    and the functions provided on the panel: remote console
                    (KVM) and remote disk. The ability to issue the CLI
                    console command to start an SOL session to a blade will
                    also require this authority."
                    ::= { remoteAccessRBSroleEntry 11 }

      rbsBladeConfiguration OBJECT-TYPE
                    SYNTAX  INTEGER {
                       disabled(0),
                       enabled(1)
                    }
                    MAX-ACCESS  read-write
                    STATUS  current -- was mandatory
                    DESCRIPTION
                    "User can modify and save any blade configuration parameter."
                    ::= { remoteAccessRBSroleEntry 12 }

      rbsBladeAdministration OBJECT-TYPE
                    SYNTAX  INTEGER {
                       disabled(0),
                       enabled(1)
                    }
                    MAX-ACCESS  read-write
                    STATUS  current -- was mandatory
                    DESCRIPTION
                    "User can power on/off and restart blades, activate
                    standby blades, do firmware updates, and modify blade LEDs."
                    ::= { remoteAccessRBSroleEntry 13 }

      rbsSwitchModuleOperator OBJECT-TYPE
                    SYNTAX  INTEGER {
                       disabled(0),
                       enabled(1)
                    }
                    MAX-ACCESS  read-write
                    STATUS  current -- was mandatory
                    DESCRIPTION
                    "User has ability to browse status and properties of
                    I/O Modules, and to ping I/O Modules."
                    ::= { remoteAccessRBSroleEntry 14 }

      rbsSwitchModuleConfiguration OBJECT-TYPE
                    SYNTAX  INTEGER {
                       disabled(0),
                       enabled(1)
                    }
                    MAX-ACCESS  read-write
                    STATUS  current -- was mandatory
                    DESCRIPTION
                    "User can modify the I/O Module IP address, configure
                    I/O Module Advanced Management parameters, and restore
                    factory defaults on an I/O Module. Note that a user 
                    requires both I/O Module configuration and I/O Module 
                    administration roles in order to be able to launch a telnet
                    or web UI session to an I/O Module, or to restore factory
                    defaults on an I/O Module."
                    ::= { remoteAccessRBSroleEntry 15 }

      rbsSwitchModuleAdministration OBJECT-TYPE
                    SYNTAX  INTEGER {
                       disabled(0),
                       enabled(1)
                    }
                    MAX-ACCESS  read-write
                    STATUS  current -- was mandatory
                    DESCRIPTION
                    "User can power on/off and restart the I/O Modules,
                    update I/O Module firmware, enable/disable the Fast POST 
                    and External Ports of an I/O Module. Note that a user 
                    requires both I/O Module configuration and I/O Module
                    administration roles in order to be able to launch a telnet
                    or web UI session to an I/O Module, or to restore factory 
                    defaults on an I/O Module."
                    ::= { remoteAccessRBSroleEntry 16 }

      rbsBladeRemotePresenseVideo OBJECT-TYPE
                    SYNTAX  INTEGER {
                       disabled(0),
                       enabled(1)
                    }
                    MAX-ACCESS  read-write
                    STATUS  deprecated
                    DESCRIPTION
                    "User can browser Remote Control web panel and remote blade video.

                    NOTE: This mib object is deprecated.  This level of granularity is available
                    via the LDAP snap-in tool."
                    ::= { remoteAccessRBSroleEntry 17 }

      rbsBladeRemotePresenseKVM OBJECT-TYPE
                    SYNTAX  INTEGER {
                       disabled(0),
                       enabled(1)
                    }
                    MAX-ACCESS  read-write
                    STATUS  deprecated
                    DESCRIPTION
                    "User has ability to access the Remote Control web panel
                    and the functions provided on the panel: remote console
                    (KVM) and remote disk.
                    
                    NOTE: This mib object is deprecated.  This level of granularity is available
                    via the LDAP snap-in tool."
                    ::= { remoteAccessRBSroleEntry 18 }

      rbsBladeRemotePresenseRdriveR OBJECT-TYPE
                    SYNTAX  INTEGER {
                       disabled(0),
                       enabled(1)
                    }
                    MAX-ACCESS  read-write
                    STATUS  deprecated
                    DESCRIPTION
                    "User can mount remote blade driver, and have read access only.

                    NOTE: This mib object is deprecated.  This level of granularity is available
                    via the LDAP snap-in tool."
                    ::= { remoteAccessRBSroleEntry 19 }

      rbsBladeRemotePresenseRdriveRW OBJECT-TYPE
                    SYNTAX  INTEGER {
                       disabled(0),
                       enabled(1)
                    }
                    MAX-ACCESS  read-write
                    STATUS  deprecated
                    DESCRIPTION
                    "User can mount remote blade driver and have read/write access.

                    NOTE: This mib object is deprecated.  This level of granularity is available
                    via the LDAP snap-in tool."
                    ::= { remoteAccessRBSroleEntry 20 }

      rbsChassisRemotePresenseRdoc OBJECT-TYPE
                    SYNTAX  INTEGER {
                       disabled(0),
                       enabled(1)
                    }
                    MAX-ACCESS  read-write
                    STATUS  deprecated
                    DESCRIPTION
                    "User has ability to upload/delete own image to RDOC and also 
                     can start remote control web panel.

                    NOTE: This mib object is deprecated.  This level of granularity is available
                    via the LDAP snap-in tool."
                    ::= { remoteAccessRBSroleEntry 21 }

      rbsRemotePresenceSupervisor OBJECT-TYPE
                    SYNTAX  INTEGER {
                       disabled(0),
                       enabled(1)
                    }
                    MAX-ACCESS  read-write
                    STATUS  deprecated
                    DESCRIPTION
                    "User has ability to access the Remote Control web panel
                    and the functions provided on the panel: remote console
                    (KVM) and remote driver read/write, upload/delete himself 
                    and other's image to RDOC.

                    NOTE: This mib object is deprecated.  This level of granularity is available
                    via the LDAP snap-in tool."
                    ::= { remoteAccessRBSroleEntry 22 }

      remoteAccessRBSscopeTable  OBJECT-TYPE
                    SYNTAX  SEQUENCE OF RemoteAccessRBSscopeEntry
                    MAX-ACCESS  not-accessible
                    STATUS  current -- was mandatory
                    DESCRIPTION
                    "Table of RBS User Scope profiles."
                    ::= {  remoteAccessIds 4 }

      remoteAccessRBSscopeEntry  OBJECT-TYPE
                    SYNTAX RemoteAccessRBSscopeEntry
                    MAX-ACCESS  not-accessible
                    STATUS  current -- was mandatory
                    DESCRIPTION
                    "User Scope entries."
                    INDEX { scopeIndex }
                    ::= { remoteAccessRBSscopeTable 1 }

      RemoteAccessRBSscopeEntry ::= SEQUENCE {
                    scopeIndex INTEGER,
                    scopeId OCTET STRING,
                    rbsChassis INTEGER,
                    rbsBlade1 INTEGER,
                    rbsBlade2 INTEGER,
                    rbsBlade3 INTEGER,
                    rbsBlade4 INTEGER,
                    rbsBlade5 INTEGER,
                    rbsBlade6 INTEGER,
                    rbsBlade7 INTEGER,
                    rbsBlade8 INTEGER,
                    rbsBlade9 INTEGER,
                    rbsBlade10 INTEGER,
                    rbsBlade11 INTEGER,
                    rbsBlade12 INTEGER,
                    rbsBlade13 INTEGER,
                    rbsBlade14 INTEGER,
                    rbsSwitch1 INTEGER,
                    rbsSwitch2 INTEGER,
                    rbsSwitch3 INTEGER,
                    rbsSwitch4 INTEGER,  
                    rbsSwitch5 INTEGER,  
                    rbsSwitch6 INTEGER,  
                    rbsSwitch7 INTEGER,  
                    rbsSwitch8 INTEGER,  
                    rbsSwitch9 INTEGER,  
                    rbsSwitch10 INTEGER  
                    }


      scopeIndex    OBJECT-TYPE
                    SYNTAX  INTEGER(0..255)
                    MAX-ACCESS  read-only
                    STATUS  current -- was mandatory
                    DESCRIPTION
                    "Index for RBS User Scope Entry."
                    ::= { remoteAccessRBSscopeEntry 1 }

      scopeId       OBJECT-TYPE
                    SYNTAX  OCTET STRING (SIZE(0..16))
                    MAX-ACCESS  read-only
                    STATUS  current -- was mandatory
                    DESCRIPTION
                    "User ID"
                    ::= { remoteAccessRBSscopeEntry 2 }

      rbsChassis    OBJECT-TYPE
                    SYNTAX  INTEGER {
                       disabled(0),
                       enabled(1)
                    }
                    MAX-ACCESS  read-write
                    STATUS  current -- was mandatory
                    DESCRIPTION
                    "User has access to the MM and chassis functions."
                    ::= { remoteAccessRBSscopeEntry 3 }

      rbsBlade1     OBJECT-TYPE
                    SYNTAX  INTEGER {
                       disabled(0),
                       enabled(1)
                    }
                    MAX-ACCESS  read-write
                    STATUS  current -- was mandatory
                    DESCRIPTION
                    "User has access to the blade in slot 1."
                    ::= { remoteAccessRBSscopeEntry 4 }

      rbsBlade2     OBJECT-TYPE
                    SYNTAX  INTEGER {
                       disabled(0),
                       enabled(1)
                    }
                    MAX-ACCESS  read-write
                    STATUS  current -- was mandatory
                    DESCRIPTION
                    "User has access to the blade in slot 2."
                    ::= { remoteAccessRBSscopeEntry 5 }


      rbsBlade3     OBJECT-TYPE
                    SYNTAX  INTEGER {
                       disabled(0),
                       enabled(1)
                    }
                    MAX-ACCESS  read-write
                    STATUS  current -- was mandatory
                    DESCRIPTION
                    "User has access to the blade in slot 3."
                    ::= { remoteAccessRBSscopeEntry 6 }

      rbsBlade4     OBJECT-TYPE
                    SYNTAX  INTEGER {
                       disabled(0),
                       enabled(1)
                    }
                    MAX-ACCESS  read-write
                    STATUS  current -- was mandatory
                    DESCRIPTION
                    "User has access to the blade in slot 4."
                    ::= { remoteAccessRBSscopeEntry 7 }

      rbsBlade5     OBJECT-TYPE
                    SYNTAX  INTEGER {
                       disabled(0),
                       enabled(1)
                    }
                    MAX-ACCESS  read-write
                    STATUS  current -- was mandatory
                    DESCRIPTION
                    "User has access to the blade in slot 5."
                    ::= { remoteAccessRBSscopeEntry 8 }

      rbsBlade6     OBJECT-TYPE
                    SYNTAX  INTEGER {
                       disabled(0),
                       enabled(1)
                    }
                    MAX-ACCESS  read-write
                    STATUS  current -- was mandatory
                    DESCRIPTION
                    "User has access to the blade in slot 6."
                    ::= { remoteAccessRBSscopeEntry 9 }

      rbsBlade7     OBJECT-TYPE
                    SYNTAX  INTEGER {
                       disabled(0),
                       enabled(1)
                    }
                    MAX-ACCESS  read-write
                    STATUS  current -- was mandatory
                    DESCRIPTION
                    "User has access to the blade in slot 7."
                    ::= { remoteAccessRBSscopeEntry 10 }


      rbsBlade8     OBJECT-TYPE
                    SYNTAX  INTEGER {
                       disabled(0),
                       enabled(1)
                    }
                    MAX-ACCESS  read-write
                    STATUS  current -- was mandatory
                    DESCRIPTION
                    "User has access to the blade in slot 8."
                    ::= { remoteAccessRBSscopeEntry 11 }

      rbsBlade9     OBJECT-TYPE
                    SYNTAX  INTEGER {
                       disabled(0),
                       enabled(1)
                    }
                    MAX-ACCESS  read-write
                    STATUS  current -- was mandatory
                    DESCRIPTION
                    "User has access to the blade in slot 9."
                    ::= { remoteAccessRBSscopeEntry 12 }

      rbsBlade10    OBJECT-TYPE
                    SYNTAX  INTEGER {
                       disabled(0),
                       enabled(1)
                    }
                    MAX-ACCESS  read-write
                    STATUS  current -- was mandatory
                    DESCRIPTION
                    "User has access to the blade in slot 10."
                    ::= { remoteAccessRBSscopeEntry 13 }

      rbsBlade11    OBJECT-TYPE
                    SYNTAX  INTEGER {
                       disabled(0),
                       enabled(1)
                    }
                    MAX-ACCESS  read-write
                    STATUS  current -- was mandatory
                    DESCRIPTION
                    "User has access to the blade in slot 11."
                    ::= { remoteAccessRBSscopeEntry 14 }

      rbsBlade12    OBJECT-TYPE
                    SYNTAX  INTEGER {
                       disabled(0),
                       enabled(1)
                    }
                    MAX-ACCESS  read-write
                    STATUS  current -- was mandatory
                    DESCRIPTION
                    "User has access to the blade in slot 12."
                    ::= { remoteAccessRBSscopeEntry 15 }


      rbsBlade13    OBJECT-TYPE
                    SYNTAX  INTEGER {
                       disabled(0),
                       enabled(1)
                    }
                    MAX-ACCESS  read-write
                    STATUS  current -- was mandatory
                    DESCRIPTION
                    "User has access to the blade in slot 13."
                    ::= { remoteAccessRBSscopeEntry 16 }

      rbsBlade14    OBJECT-TYPE
                    SYNTAX  INTEGER {
                       disabled(0),
                       enabled(1)
                    }
                    MAX-ACCESS  read-write
                    STATUS  current -- was mandatory
                    DESCRIPTION
                    "User has access to the blade in slot 14."
                    ::= { remoteAccessRBSscopeEntry 17 }

      rbsSwitch1    OBJECT-TYPE
                    SYNTAX  INTEGER {
                       disabled(0),
                       enabled(1)
                    }
                    MAX-ACCESS  read-write
                    STATUS  current -- was mandatory
                    DESCRIPTION
                    "User has access to I/O module 1."
                    ::= { remoteAccessRBSscopeEntry 18 }

      rbsSwitch2    OBJECT-TYPE
                    SYNTAX  INTEGER {
                       disabled(0),
                       enabled(1)
                    }
                    MAX-ACCESS  read-write
                    STATUS  current -- was mandatory
                    DESCRIPTION
                    "User has access to I/O module 2."
                    ::= { remoteAccessRBSscopeEntry 19 }

      rbsSwitch3    OBJECT-TYPE
                    SYNTAX  INTEGER {
                       disabled(0),
                       enabled(1)
                    }
                    MAX-ACCESS  read-write
                    STATUS  current -- was mandatory
                    DESCRIPTION
                    "User has access to I/O module 3."
                    ::= { remoteAccessRBSscopeEntry 20 }

      rbsSwitch4    OBJECT-TYPE
                    SYNTAX  INTEGER {
                       disabled(0),
                       enabled(1)
                    }
                    MAX-ACCESS  read-write
                    STATUS  current -- was mandatory
                    DESCRIPTION
                    "User has access to I/O module 4."
                    ::= { remoteAccessRBSscopeEntry 21 }
                    
      rbsSwitch5    OBJECT-TYPE
                    SYNTAX  INTEGER {
                       disabled(0),
                       enabled(1)
                    }
                    MAX-ACCESS  read-write
                    STATUS  current -- was mandatory
                    DESCRIPTION
                    "User has access to I/O module 5."
                    ::= { remoteAccessRBSscopeEntry 22 }
                    
      rbsSwitch6    OBJECT-TYPE
                    SYNTAX  INTEGER {
                       disabled(0),
                       enabled(1)
                    }
                    MAX-ACCESS  read-write
                    STATUS  current -- was mandatory
                    DESCRIPTION
                    "User has access to I/O module 6."
                    ::= { remoteAccessRBSscopeEntry 23 }

      rbsSwitch7    OBJECT-TYPE
                    SYNTAX  INTEGER {
                       disabled(0),
                       enabled(1)
                    }
                    MAX-ACCESS  read-write
                    STATUS  current -- was mandatory
                    DESCRIPTION
                    "User has access to I/O module 7."
                    ::= { remoteAccessRBSscopeEntry 24 }
                    
                    
      rbsSwitch8    OBJECT-TYPE
                    SYNTAX  INTEGER {
                       disabled(0),
                       enabled(1)
                    }
                    MAX-ACCESS  read-write
                    STATUS  current -- was mandatory
                    DESCRIPTION
                    "User has access to I/O module 8."
                    ::= { remoteAccessRBSscopeEntry 25 }
                    
      rbsSwitch9    OBJECT-TYPE
                    SYNTAX  INTEGER {
                       disabled(0),
                       enabled(1)
                    }
                    MAX-ACCESS  read-write
                    STATUS  current -- was mandatory
                    DESCRIPTION
                    "User has access to I/O module 9."
                    ::= { remoteAccessRBSscopeEntry 26 }
                    
      rbsSwitch10   OBJECT-TYPE
                    SYNTAX  INTEGER {
                       disabled(0),
                       enabled(1)
                    }
                    MAX-ACCESS  read-write
                    STATUS  current -- was mandatory
                    DESCRIPTION
                    "User has access to I/O module 10."
                    ::= { remoteAccessRBSscopeEntry 27 }
    
    -- ********************************************************************************
    -- Enable/Disable User Interfaces
    -- ********************************************************************************
    userInterfaces OBJECT IDENTIFIER ::= { remoteAccessConfig 5 }
      cli           OBJECT-TYPE
                    SYNTAX  INTEGER {
                       disabled(0),
                       telnet-only(1),
                       ssh-only(2),
                       enabled(3)
                    }
                    MAX-ACCESS  read-write
                    STATUS  current -- was mandatory
                    DESCRIPTION
                    "Enable/Disable CLI access to the MM (telnet and SSH).
                    The value enabled(3) means both telnet and ssh are enabled."
                    ::= { userInterfaces 1 }

      snmp          OBJECT-TYPE
                    SYNTAX  INTEGER {
                       disabled(0),
                       v1-only(1),
                       v3-only(2),
                       enabled(3)
                    }
                    MAX-ACCESS  read-write
                    STATUS  current -- was mandatory
                    DESCRIPTION
                    "Enable/Disable SNMP v1 and v3 access to the MM."
                    ::= { userInterfaces 2 }

      tcm           OBJECT-TYPE
                    SYNTAX  INTEGER (0..20)
                    MAX-ACCESS  read-write
                    STATUS  current -- was mandatory
                    DESCRIPTION
                    "Enable/Disable TCM access to the MM.
                     A value of 0 means disabled, any value from 1 to 20 means enabled.
                     NOTE: AMM will provide a max of 20 connections for both 
                     Secure TCP Command Mode and TCP Command Mode."
                    ::= { userInterfaces 3 }

      web           OBJECT-TYPE
                    SYNTAX  INTEGER {
                       disabled(0),
                       enabled(1)
                    }
                    MAX-ACCESS  read-write
                    STATUS  current -- was mandatory
                    DESCRIPTION
                    "Enable/Disable Web access (HTTP/HTTPS) to the MM. 

                     NOTE: Disabling web access to the MM will cause all
                           currently active web sessions to disconnect, 
                           and you will no longer be able to access the 
                           MM management functions using a web browser."
                    ::= { userInterfaces 4 }

      stcm           OBJECT-TYPE
                    SYNTAX  INTEGER (0..20)
                    MAX-ACCESS  read-write
                    STATUS  current -- was mandatory
                    DESCRIPTION
                    "Enable/Disable STCM access to the MM.
                     A value of 0 means disabled, any value from 1 to 20 means enabled.
                     NOTE: AMM will provide a max of 20 connections for both
                           Secure TCP Command Mode and TCP Command Mode.
                           If no valid server certificate is in place, 
                           Secure TCP Command Mode will not be allowed to set to enable."
                    ::= { userInterfaces 5 }

    -- ---------------------------------------------------------- --
    -- The Remote Access ID SSH Client Authentication Public Key Group
    -- ---------------------------------------------------------- --
    mmSshClientAuth OBJECT IDENTIFIER ::= { remoteAccessConfig 6 }

    mmSshClientAuthPubKeyTable OBJECT-TYPE
        SYNTAX      SEQUENCE OF MmSshClientAuthPubKeyEntry
        MAX-ACCESS      not-accessible
        STATUS      current -- was mandatory
        DESCRIPTION
        "A table that contains client authentication
        public key information."
        ::= { mmSshClientAuth 1 }

    mmSshClientAuthPubKeyEntry OBJECT-TYPE
        SYNTAX      MmSshClientAuthPubKeyEntry
        MAX-ACCESS      not-accessible
        STATUS      current -- was mandatory
        DESCRIPTION
        "A information list about a particular SSH 
        public key used for client authentication.
        The primary table index is the same value as
        the associated remoteAccessIdEntryIndex.
        The secondary table index allows selection 
        of the Nth public key for that 
        remoteAccessIdEntryIndex."
        INDEX { mmSshClientAuthRemoteAccessIdIndex ,
                mmSshClientAuthPubKeyIndex }
        ::= { mmSshClientAuthPubKeyTable 1 }

    MmSshClientAuthPubKeyEntry ::=
        SEQUENCE {
            mmSshClientAuthRemoteAccessIdIndex      INTEGER,
            mmSshClientAuthPubKeyIndex              INTEGER,
            mmSshClientAuthPubKeyType               INTEGER,
            mmSshClientAuthPubKeySize               INTEGER,
            mmSshClientAuthPubKeyFingerprint        OCTET STRING,
            mmSshClientAuthPubKeyAcceptFrom         OCTET STRING,
            mmSshClientAuthPubKeyComment            OCTET STRING,
            mmSshClientAuthPubKeyAction             INTEGER,
            mmSshClientAuthPubKeyEntryStatus        EntryStatus
        }

    mmSshClientAuthRemoteAccessIdIndex  OBJECT-TYPE
        SYNTAX      Integer32 (0..2147483647) -- was INTEGER
        MAX-ACCESS      not-accessible
        STATUS      current -- was mandatory
        DESCRIPTION 
        "The primary table index is the same value as
        the associated remoteAccessIdEntryIndex used 
        as an index into the remoteAccessIdsTable."
        ::= { mmSshClientAuthPubKeyEntry 1 }
        
    mmSshClientAuthPubKeyIndex  OBJECT-TYPE
        SYNTAX  Integer32 (0..2147483647) -- was INTEGER
        MAX-ACCESS  not-accessible
        STATUS  current -- was mandatory
        DESCRIPTION
        "The secondary table index used to select 
         one of the client authentication public 
         keys for a particular remote access Id.
         The index is an integer value from 1 to N
         where N is the number of keys associated 
         with a particular remote access Id. 
         An addition always causes the value of N to increase
         by one, effectively adding an entry after the 
         existing keys for that remote access Id.
         If an entry is deleted from the table by 
         setting mmSshClientAuthPubKeyEntryStatus = invalid,
         the key associated with that entry is deleted.  
         If the deleted key was not the last key for 
         a remote access Id (mmSshClientAuthPubKeyIndex is 
         not the 'last' or Nth entry), the subsequent entries
         are renumbered after the deletion. A deletion 
         always causes the value of N to decrease by one. 
         The underlying SSH server implementation searches
         the keys in order from 1 to N when attempting public 
         key authentication.
         
         NOTE:A maximum of 4 public keys can be installed
         for one remote access Id."
        ::= { mmSshClientAuthPubKeyEntry 2 }

    mmSshClientAuthPubKeyType     OBJECT-TYPE
        SYNTAX  INTEGER { 
            sshDss   (1), 
            sshRsa   (2)
        }
        MAX-ACCESS        read-only
        STATUS        current -- was mandatory
        DESCRIPTION
        "The type of the SSH public key represented by
         this entry."
        ::= { mmSshClientAuthPubKeyEntry 3 }

    mmSshClientAuthPubKeySize          OBJECT-TYPE
        SYNTAX  INTEGER { 
            bits512   (1), 
            bits768   (2),
            bits1024  (3),
            bits2048  (4),
            bits4096  (5)
        }
        MAX-ACCESS        read-only
        STATUS        current -- was mandatory
        DESCRIPTION
        "The size of the SSH public key represented by
        this entry."
        ::= { mmSshClientAuthPubKeyEntry 4 }

    mmSshClientAuthPubKeyFingerprint   OBJECT-TYPE
        SYNTAX        OCTET STRING
        MAX-ACCESS        read-only
        STATUS        current -- was mandatory
        DESCRIPTION
        "The RSA fingerprint of the SSH public key represented 
        by this entry.
        This value can be used with the SSH client to
        verify, on the initial connection, that the Secure Shell
        server responding to the request is the server running
        on the managed entity.  This is the fingerprint of the
        operational host key pair.  If the key pair represented
        by this entry is not operational then sixteen null octets
        must be returned."
        ::= { mmSshClientAuthPubKeyEntry 5 }

    mmSshClientAuthPubKeyAcceptFrom   OBJECT-TYPE
        SYNTAX        OCTET STRING
        MAX-ACCESS        read-write
        STATUS        current -- was mandatory
        DESCRIPTION
        "This is a filter that describes the set of SSH client 
        IP addresses and host names that can establish     
        SSH connections to the AMM authenticated by the public key 
        represented by this entry of the table. The filter is a 
        comma-separated list of IP addresses and/or hostnames. 
        A question mark may be used to match any single character.
        An asterisk may be used to match multiple characters.
        An exclamation point may preceed an IP address or hostname
        to deny acccess from that IP address or hostname.
        
        The format of the Accept From specification is:
                    from=PATTERN-LIST
        PATTERN-LIST is the filter, which must be enclosed in 
        double quotation marks.
        
        NOTE:This MIB object can be manipulated after the
        corresponding SSH public key is installed."
        ::= { mmSshClientAuthPubKeyEntry 6 }

    mmSshClientAuthPubKeyComment   OBJECT-TYPE
        SYNTAX        OCTET STRING
        MAX-ACCESS        read-write
        STATUS        current -- was mandatory
        DESCRIPTION
        "This is a descriptive string that the administrator may 
        use to help identify the public key represented by this entry. 
        It serves no function in the operation of the SSH server.
        
        NOTE:This MIB object can be manipulated after the
        corresponding SSH public key is installed."
        ::= { mmSshClientAuthPubKeyEntry 7 }

    mmSshClientAuthPubKeyAction    OBJECT-TYPE
        SYNTAX INTEGER { 
          import(1),
          export(2)
        }  
        MAX-ACCESS  read-write
        STATUS  current -- was mandatory
        DESCRIPTION
        "import(1) starts the TFTP file transfer of an SSH 
        client authentication public key from the TFTP 
        server to the AMM. The import operation is only 
        accepted if the associated RemoteAccessIdsEntry row
        is configured and the current value of 
        mmSshClientAuthPubKeyEntryStatus is underCreation(3)
        or valid(1), if the current value of mmSshClientAuthPubKeyEntryStatus
        is valid(1), it will replace the key with a new key, 
        If the import is successful the value of 
        mmSshClientAuthPubKeyRowStatus changes to valid(1).
        export(2) starts the TFTP file transfer of an SSH 
        client authentication public key from the AMM to the TFTP
        server.  The export operation is only accepted if 
        the current value of mmSshClientAuthPubKeyEntryStatus
        is valid(1).
          
        NOTE: Users should compare the fingerprint value
        mmSshClientAuthPubKeyFingerprint to the 
        fingerprint of client authentication key files 
        imported or exported using the TFTP file transfer
        protocol to guard against possible file corruption.
        
        Value returned for the GET command is meaningless 
        for this MIB object."
        ::= { mmSshClientAuthPubKeyEntry 8 }

    mmSshClientAuthPubKeyEntryStatus     OBJECT-TYPE
        SYNTAX      EntryStatus
        MAX-ACCESS      read-write
        STATUS      current -- was mandatory
        DESCRIPTION
        "This object manages the creation and deletion of this entry.
        The steps recommended to install and to activate a new client 
        authorization public key are:
        1. Set values for mmSshClientAuthPubKeyTftpServer,
           mmSshClientAuthPubKeyFileName, mmSshClientAuthPubKeyFileFormat 
        2. Create a new entry in this table 
           mmSshClientAuthPubKeyEntryStatus = createRequest
        3. Import a new key mmSshClientAuthPubKeyAction = import
           This entry will be valid after mmSshClientAuthPubKeyAction
           is successfully imported.
        4. Set mmSshClientAuthPubKeyAcceptFrom and
           mmSshClientAuthPubKeyComment as required. 

        valid(1)        - Indicates that the public key pair represented
                          by this entry is available for use by the Secure
                          Shell Server for client authentication. 
                             
        createRequest(2) - A new entry will be created in this table
                           for the specified host key pair and the new
                           entry will transition to the underCreation(3)
                           state. The operation is only accepted if the
                           associated RemoteAccessIdsEntry row defining
                           a local user account is configured.

        underCreation(3) - Indicates that this entry exists in the
                           agent but is unavailable for use. After completing the
                           create operation, the agent will set this object to
                           underCreation(3).
                              
        invalid(4)    - Deletes this entry and any client authentication 
                        public key that may be associated with it." 
        ::= { mmSshClientAuthPubKeyEntry 9 }
        
    mmSshClientAuthPubKeyUnused OBJECT-TYPE
                    SYNTAX  INTEGER
                    MAX-ACCESS  read-only 
                    STATUS  current -- was mandatory
                    DESCRIPTION
                    "The number of available storage locations that may be 
                    used to install additional Client Authentication 
                    Public Keys. This number decreases by one when a new
                    key is added to the configuration." 
                    ::= { mmSshClientAuth 2 }

    mmSshClientAuthPubKeyTftpServer   OBJECT-TYPE
                    SYNTAX  OCTET STRING
                    MAX-ACCESS  read-write
                    STATUS  current -- was mandatory
                    DESCRIPTION
                    "IP address or host name of the TFTP server where an SSH client
                    authentication public key is to be installed from or exported 
                    to. The address must be entered in a dotted decimal 
                    IP string (e.g. 9.37.44.2)."
                    ::= { mmSshClientAuth 3 }
    
    mmSshClientAuthPubKeyFileName      OBJECT-TYPE
                    SYNTAX  OCTET STRING
                    MAX-ACCESS  read-write
                    STATUS  current -- was mandatory
                    DESCRIPTION
                    "File name on the TFTP server of an SSH client
                    authentication public key."
                    ::= { mmSshClientAuth 4 }
                    
    mmSshClientAuthPubKeyFileFormat      OBJECT-TYPE
                    SYNTAX    INTEGER { 
                        openSSH (1),
                        rfc4716 (2) 
                    }
                    MAX-ACCESS  read-write
                    STATUS  current -- was mandatory
                    DESCRIPTION
                    "File format of SSH client authentication public key files 
                    imported from or exported to the TFTP file server."
                    ::= { mmSshClientAuth 5 }
                    
    -- ********************************************************************************
    -- Remote Alert types
    -- ********************************************************************************
    remoteAlerts  OBJECT IDENTIFIER ::= { configureSP 2 }

     -- ********************************************************************************
     -- Remote Alert Critical Error types
     -- ********************************************************************************
     remoteAlertsCrit  OBJECT IDENTIFIER ::= { remoteAlerts 1 }

      critTemp     OBJECT-TYPE
                   SYNTAX  INTEGER {
                     disabled(0),
                     enabled(1)
                   }
                   MAX-ACCESS  read-write
                   STATUS  deprecated
                   DESCRIPTION
                   "Generate an alert if any of the monitored temperature sensors
                   in the system exceed their critical threshold.

                   NOTE: If a critical Temperature condition is detected,
                   the server will automatically be shut down and powered off
                   whether this object is enabled or not.
                   NOTE: This mib object will be replaced in a future release."
                   ::= { remoteAlertsCrit 1 }
      
      critVolt     OBJECT-TYPE
                   SYNTAX  INTEGER {
                     disabled(0),
                     enabled(1)
                   }
                   MAX-ACCESS  read-write
                   STATUS  deprecated
                   DESCRIPTION
                   "Generate a alert if any of the monitored power supply sensors 
                   in the system fall outside their specified critical 
                   operational range.
                   
                   NOTE: If a critical voltage condition is detected, 
                   the server will automatically be shut down and powered off 
                   whether this object is enabled or not.
                   This mib object will be replaced in a future release."
                   ::= { remoteAlertsCrit 2 }


      critMultiBlower OBJECT-TYPE
                   SYNTAX  INTEGER {
                     disabled(0),
                     enabled(1)
                   }
                   MAX-ACCESS  read-write
                   STATUS  deprecated
                   DESCRIPTION
                   "Generate an alert if multiple blowers used for cooling the system fail.

                   NOTE: Blowers are also referred to as Chassis Cooling Devices.
                   NOTE: This mib object will be replaced in a future release."
                   ::= { remoteAlertsCrit 4 }

      critPower    OBJECT-TYPE
                   SYNTAX  INTEGER {
                     disabled(0),
                     enabled(1)
                   }
                   MAX-ACCESS  read-write
                   STATUS  current -- was mandatory
                   DESCRIPTION
                   "Generate an alert if any of the system power supplies fail."
                   ::= { remoteAlertsCrit 5 }

      critHardDrive OBJECT-TYPE
                   SYNTAX  INTEGER {
                     disabled(0),
                     enabled(1)
                   }
                   MAX-ACCESS  read-write
                   STATUS  deprecated
                   DESCRIPTION
                   "Generate an alert if any of hard disk drives fail.
                   NOTE: This mib object will be replaced in a future release."
                   ::= { remoteAlertsCrit 6 }

      critVRM      OBJECT-TYPE
                   SYNTAX  INTEGER {
                     disabled(0),
                     enabled(1)
                   }
                   MAX-ACCESS  read-write
                   STATUS  deprecated
                   DESCRIPTION
                   "Generate an alert if any of VRM (voltage regulator modules) fail.
                   NOTE: This mib object will be replaced in a future release."
                   ::= { remoteAlertsCrit 7 }


      critMultipleSwitchModule  OBJECT-TYPE
                   SYNTAX  INTEGER {
                     disabled(0),
                     enabled(1)
                   }
                   MAX-ACCESS  read-write
                   STATUS  deprecated
                   DESCRIPTION
                   "Generate an alert if all switch modules fail or are removed.
                   NOTE: This mib object will be replaced in a future release."
                   ::= { remoteAlertsCrit 8 }

      critInvalidConfig  OBJECT-TYPE
                   SYNTAX  INTEGER {
                     disabled(0),
                     enabled(1)
                   }
                   MAX-ACCESS  read-write
                   STATUS  deprecated
                   DESCRIPTION
                   "Generate an alert if the hardware configuration is incompatible.
                   NOTE: This mib object will be replaced in a future release."
                   ::= { remoteAlertsCrit 9 }

      critBlade  OBJECT-TYPE
                   SYNTAX  INTEGER {
                     disabled(0),
                     enabled(1)
                   }
                   MAX-ACCESS  read-write
                   STATUS  current -- was mandatory
                   DESCRIPTION
                   "Generate an alert for any critical error condition on a blade."
                   ::= { remoteAlertsCrit 10 }

      critIO  OBJECT-TYPE
                   SYNTAX  INTEGER {
                     disabled(0),
                     enabled(1)
                   }
                   MAX-ACCESS  read-write
                   STATUS  current -- was mandatory
                   DESCRIPTION
                   "Generate an alert for any critical error condition on I/O module."
                   ::= { remoteAlertsCrit 11 }

      critStorage  OBJECT-TYPE
                   SYNTAX  INTEGER {
                     disabled(0),
                     enabled(1)
                   }
                   MAX-ACCESS  read-write
                   STATUS  current -- was mandatory
                   DESCRIPTION
                   "Generate an alert for any critical error condition on a Storage module.

                   NOTE: This MIB object is for BCS only."
                   ::= { remoteAlertsCrit 12 }

      critChassis  OBJECT-TYPE
                   SYNTAX  INTEGER {
                     disabled(0),
                     enabled(1)
                   }
                   MAX-ACCESS  read-write
                   STATUS  current -- was mandatory
                   DESCRIPTION
                   "Generate an alert for any critical error condition on chassis."
                   ::= { remoteAlertsCrit 13 }   

      critFan  OBJECT-TYPE
                   SYNTAX  INTEGER {
                     disabled(0),
                     enabled(1)
                   }
                   MAX-ACCESS  read-write
                   STATUS  current -- was mandatory
                   DESCRIPTION
                   "Generate an alert for any critical error condition on cooling devices."
                   ::= { remoteAlertsCrit 14 }

     -- ********************************************************************************
     -- Remote Alert Warning(non-critical) Error types
     -- ********************************************************************************
     remoteAlertsNonCrit  OBJECT IDENTIFIER ::= { remoteAlerts 2 }

      warnSingleBlower OBJECT-TYPE
                    SYNTAX  INTEGER {
                      disabled(0),
                      enabled(1)
                    }
                    MAX-ACCESS  read-write
                    STATUS  deprecated
                    DESCRIPTION
                    "Generate an alert if one blower used for cooling the system fails.

                    NOTE: Blowers are also referred to as Chassis Cooling Devices.
                    NOTE: This mib object will be replaced in a future release."
                    ::= { remoteAlertsNonCrit 2 }

      warnTemp     OBJECT-TYPE
                   SYNTAX  INTEGER {
                     disabled(0),
                     enabled(1)
                   }
                   MAX-ACCESS  read-write
                   STATUS  deprecated
                   DESCRIPTION
                   "Generate an alert if any of the monitored temperature sensors
                   in the system exceed their warning threshold.

                   NOTE: Blowers are also referred to as Chassis Cooling Devices.
                   NOTE: This mib object will be replaced in a future release."
                   ::= { remoteAlertsNonCrit 3 }

      warnVoltage  OBJECT-TYPE
                   SYNTAX  INTEGER {
                     disabled(0),
                     enabled(1)
                   }
                   MAX-ACCESS  read-write
                   STATUS  deprecated
                   DESCRIPTION
                   "Generate an alert if any of the monitored power supply sensors
                   in the system fall outside their specified warning operational range.
                   NOTE: This mib object will be replaced in a future release."
                   ::= { remoteAlertsNonCrit 4 }

      warnRedundantModule  OBJECT-TYPE
                   SYNTAX  INTEGER {
                     disabled(0),
                     enabled(1)
                   }
                   MAX-ACCESS  read-write
                   STATUS  deprecated
                   DESCRIPTION
                   "Generate an alert if any of the switch modules or management
                   modules is failing or removed.
                   NOTE: This mib object will be replaced in a future release."
                   ::= { remoteAlertsNonCrit 6 }

      warnMediaTrayKVMSwitch  OBJECT-TYPE
                   SYNTAX  INTEGER {
                     disabled(0),
                     enabled(1)
                   }
                   MAX-ACCESS  read-write
                   STATUS  deprecated
                   DESCRIPTION
                   "Generate an alert if the system detects a Media Tray or KVM
                   switching failure.
                   NOTE: This mib object will be replaced in a future release."
                   ::= {  remoteAlertsNonCrit 7 }

      warnLogFull  OBJECT-TYPE
                   SYNTAX  INTEGER {
                     disabled(0),
                     enabled(1)
                   }
                   MAX-ACCESS  read-write
                   STATUS  current -- was mandatory
                   DESCRIPTION
                   "Generate an alert if the system log reaches 100% full."
                   ::= { remoteAlertsNonCrit 10 }

      warnBlade  OBJECT-TYPE
                   SYNTAX  INTEGER {
                     disabled(0),
                     enabled(1)
                   }
                   MAX-ACCESS  read-write
                   STATUS  current -- was mandatory
                   DESCRIPTION
                   "Generate an alert for any warning condition on a blade."
                   ::= {  remoteAlertsNonCrit 15 }

      warnIO  OBJECT-TYPE
                   SYNTAX  INTEGER {
                     disabled(0),
                     enabled(1)
                   }
                   MAX-ACCESS  read-write
                   STATUS  current -- was mandatory
                   DESCRIPTION
                   "Generate an alert for any warning condition on I/O module."
                   ::= {  remoteAlertsNonCrit 16 }

      warnStorage  OBJECT-TYPE
                   SYNTAX  INTEGER {
                     disabled(0),
                     enabled(1)
                   }
                   MAX-ACCESS  read-write
                   STATUS  current -- was mandatory
                   DESCRIPTION
                   "Generate an alert for any warning condition on a Storage module.

                   NOTE: This MIB object is for BCS only."
                   ::= {  remoteAlertsNonCrit 17 }

      warnPower  OBJECT-TYPE
                   SYNTAX  INTEGER {
                     disabled(0),
                     enabled(1)
                   }
                   MAX-ACCESS  read-write
                   STATUS  current -- was mandatory
                   DESCRIPTION
                   "Generate an alert for any warning condition on power module."
                   ::= {  remoteAlertsNonCrit 18 }
                   
      warnChassis  OBJECT-TYPE
                   SYNTAX  INTEGER {
                     disabled(0),
                     enabled(1)
                   }
                   MAX-ACCESS  read-write
                   STATUS  current -- was mandatory
                   DESCRIPTION
                   "Generate an alert for any warning condition on chassis."
                   ::= {  remoteAlertsNonCrit 19 }

      warnFan  OBJECT-TYPE
                   SYNTAX  INTEGER {
                     disabled(0),
                     enabled(1)
                   }
                   MAX-ACCESS  read-write
                   STATUS  current -- was mandatory
                   DESCRIPTION
                   "Generate an alert for any warning condition on cooling devices."
                   ::= {  remoteAlertsNonCrit 20 }

     -- ********************************************************************************
     -- Remote Alert System Error types
     -- ********************************************************************************
     remoteAlertsSystem  OBJECT IDENTIFIER ::= { remoteAlerts 3 }


      systemPowerOff OBJECT-TYPE
                   SYNTAX  INTEGER {
                     disabled(0),
                     enabled(1)
                   }
                   MAX-ACCESS  read-write
                   STATUS  deprecated
                   DESCRIPTION
                   "Generate an alert if the system is powered off.
                   NOTE: This mib object will be replaced in a future release."
                   ::= { remoteAlertsSystem 4 }

      systemPowerOn  OBJECT-TYPE
                   SYNTAX  INTEGER {
                     disabled(0),
                     enabled(1)
                   }
                   MAX-ACCESS  read-write
                   STATUS  deprecated
                   DESCRIPTION
                   "Generate a alert if the system is powered on.
                   NOTE: This mib object will be replaced in a future release."
                   ::= { remoteAlertsSystem 5 }

      systemPFA    OBJECT-TYPE
                   SYNTAX  INTEGER {
                     disabled(0),
                     enabled(1)
                   }
                   MAX-ACCESS  read-write
                   STATUS  deprecated
                   DESCRIPTION
                   "Generate a alert if the system hardware detects a Predictive
                   Failure Analysis(PFA) on PFA enabled hardware.
                   NOTE: This mib object will be replaced in a future release."
                   ::= {  remoteAlertsSystem 8 }

      systemInventory  OBJECT-TYPE
                   SYNTAX  INTEGER {
                     disabled(0),
                     enabled(1)
                   }
                   MAX-ACCESS  read-write
                   STATUS  current -- was mandatory
                   DESCRIPTION
                   "Generate an alert if the a processor blade or media tray is
                   added or removed."
                   ::= {  remoteAlertsSystem 10 }

      systemLog75PctFull  OBJECT-TYPE
                   SYNTAX  INTEGER {
                     disabled(0),
                     enabled(1)
                   }
                   MAX-ACCESS  read-write
                   STATUS  current -- was mandatory
                   DESCRIPTION
                   "Generate an alert if the system log reaches 75% full."
                   ::= {  remoteAlertsSystem 11 }

      networkChangeNotification OBJECT-TYPE
                   SYNTAX  INTEGER {
                     disabled(0),
                     enabled(1)
                   }
                   MAX-ACCESS  read-write
                   STATUS  current -- was mandatory
                   DESCRIPTION
                   "Generate an alert if the SP has restarted and the internal
                   network has initialized successfully, or if an IP address
                   change via a source other than the management module."
                   ::= {  remoteAlertsSystem 12 }

      systemBladeThrottling  OBJECT-TYPE
                   SYNTAX  INTEGER {
                     disabled(0),
                     enabled(1)
                   }
                   MAX-ACCESS  read-write
                   STATUS  deprecated
                   DESCRIPTION
                   "Generate an alert if any of the server blades are throttling.
                   NOTE: This mib object will be replaced in a future release."
                   ::= {  remoteAlertsSystem 13 }

      systemPowerManagement  OBJECT-TYPE
                   SYNTAX  INTEGER {
                     disabled(0),
                     enabled(1)
                   }
                   MAX-ACCESS  read-write
                   STATUS  deprecated
                   DESCRIPTION
                   "Generate an alert if the system detects a power oversubscription 
                   condition or power supply mismatch in a power domain.
                   NOTE: This mib object will be replaced in a future release."
                   ::= {  remoteAlertsSystem 14 }

      systemRemoteLogin  OBJECT-TYPE
                   SYNTAX  INTEGER {
                     disabled(0),
                     enabled(1)
                   }
                   MAX-ACCESS  read-write
                   STATUS  current -- was mandatory
                   DESCRIPTION
                   "Generate an alert if the system detects a new user logged in from 
                   a remote site." 
                   ::= {  remoteAlertsSystem 15 }

      systemBlade  OBJECT-TYPE
                   SYNTAX  INTEGER {
                     disabled(0),
                     enabled(1)
                   }
                   MAX-ACCESS  read-write
                   STATUS  current -- was mandatory
                   DESCRIPTION
                   "Generate an alert for any informational condition on a blade." 
                   ::= {  remoteAlertsSystem 16 }

      systemIO  OBJECT-TYPE
                   SYNTAX  INTEGER {
                     disabled(0),
                     enabled(1)
                   }
                   MAX-ACCESS  read-write
                   STATUS  current -- was mandatory
                   DESCRIPTION
                   "Generate an alert for any informational condition on I/O module." 
                   ::= {  remoteAlertsSystem 17 }

      systemStorage  OBJECT-TYPE
                   SYNTAX  INTEGER {
                     disabled(0),
                     enabled(1)
                   }
                   MAX-ACCESS  read-write
                   STATUS  current -- was mandatory
                   DESCRIPTION
                   "Generate an alert for any informational condition on a Storage module.

                   NOTE: This MIB object is for BCS only."
                   ::= {  remoteAlertsSystem 18 }

      systemPower  OBJECT-TYPE
                   SYNTAX  INTEGER {
                     disabled(0),
                     enabled(1)
                   }
                   MAX-ACCESS  read-write
                   STATUS  current -- was mandatory
                   DESCRIPTION
                   "Generate an alert for any informational condition on power module." 
                   ::= {  remoteAlertsSystem 19 }

      systemChassis  OBJECT-TYPE
                   SYNTAX  INTEGER {
                     disabled(0),
                     enabled(1)
                   }
                   MAX-ACCESS  read-write
                   STATUS  current -- was mandatory
                   DESCRIPTION
                   "Generate an alert for any informational condition on chassis." 
                   ::= {  remoteAlertsSystem 20}

      systemFan  OBJECT-TYPE
                   SYNTAX  INTEGER {
                     disabled(0),
                     enabled(1)
                   }
                   MAX-ACCESS  read-write
                   STATUS  current -- was mandatory
                   DESCRIPTION
                   "Generate an alert for any informational condition on cooling device." 
                   ::= {  remoteAlertsSystem 21}

      systemPWRDO  OBJECT-TYPE
                   SYNTAX  INTEGER {
                     disabled(0),
                     enabled(1)
                   }
                   MAX-ACCESS  read-write
                   STATUS  current -- was mandatory
                   DESCRIPTION
                   "Generate an alert for any informational condition on power on and power off." 
                   ::= {  remoteAlertsSystem 22}
     -- Flag to select whether the alert categories function in the legacy mode or
     -- the enhanced mode. 
           alertMode  OBJECT-TYPE
                   SYNTAX  INTEGER {
                     legacy(0),
                     enhanced(1)
                   }
                   MAX-ACCESS  read-write
                   STATUS  current -- was mandatory
                   DESCRIPTION
                   "Selects which alert categories will be displayed on the
                   web interface, which alert category objects are accessible
                   through SNMP, and which SNMP trap type an alert is associated with. 
                   If the enhanced option is selected then the component based
                   category scheme is used. If legacy is selected then the
                   alert type based category scheme is used. This object and the
                   legacy alerts will be removed from the MIB in a future release." 
                   ::= {  remoteAlerts 4 }
     -- ********************************************************************************
     -- Users
     -- ********************************************************************************
     --
     users  OBJECT IDENTIFIER ::= { monitors 17 }

      -- ********************************************************************************
      -- MM Users 
      -- ********************************************************************************
      -- 
      mmUsers  OBJECT IDENTIFIER ::= { users 1 }

       currentlyLoggedInTable  OBJECT-TYPE
                     SYNTAX  SEQUENCE OF CurrentlyLoggedInEntry
                     MAX-ACCESS  not-accessible
                     STATUS  current -- was mandatory
                     DESCRIPTION
                     "Table of MM users currently logged in.
                           
                     NOTE: This MIB object is for AMM only."
                     ::= {  mmUsers 1 }

       currentlyLoggedInEntry  OBJECT-TYPE
                     SYNTAX CurrentlyLoggedInEntry
                     MAX-ACCESS  not-accessible
                     STATUS  current -- was mandatory
                     DESCRIPTION
                     "MM users currently logged in entries.
                             
                     NOTE: This MIB object is for AMM only."
                     INDEX { currentlyLoggedInEntryIndex }
                     ::= { currentlyLoggedInTable 1 }

       CurrentlyLoggedInEntry ::= SEQUENCE {
                    currentlyLoggedInEntryIndex INTEGER,
                    currentlyLoggedInEntryUserId OCTET STRING,
                    currentlyLoggedInEntryAccMethod OCTET STRING
                    }

       currentlyLoggedInEntryIndex  OBJECT-TYPE
                          SYNTAX  INTEGER(0..255)
                          MAX-ACCESS  read-only
                          STATUS  current -- was mandatory
                          DESCRIPTION
                          "Index for MM users currently logged in."
                                
                          ::= { currentlyLoggedInEntry 1 }

       currentlyLoggedInEntryUserId   OBJECT-TYPE                       
                          SYNTAX  OCTET STRING (SIZE(0..64))
                          MAX-ACCESS  read-only
                          STATUS  current -- was mandatory
                          DESCRIPTION
                          "Name for MM users currently logged in.  
                          NOTE: 'Default SNMPv1 user' indicates an internal user used by SNMPv1 agent."
                                
                          ::= { currentlyLoggedInEntry 2 }

       currentlyLoggedInEntryAccMethod  OBJECT-TYPE
                          SYNTAX  OCTET STRING (SIZE(0..32))
                          MAX-ACCESS  read-only
                          STATUS  current -- was mandatory
                          DESCRIPTION
                          "Access method for MM users currently logged in."
                                
                          ::= { currentlyLoggedInEntry 3 }


     -- ********************************************************************************
     -- Front Bezel                
     -- ********************************************************************************
     frontbezel OBJECT IDENTIFIER ::= { monitors 12 }

     frontbezelExists    OBJECT-TYPE
                         SYNTAX  INTEGER {
                             false(0),
                             true(1)
                         }
                         MAX-ACCESS  read-only
                         STATUS  current -- was mandatory
                         DESCRIPTION
                         "Indicates whether the front bezel is installed or not.
                              
                         NOTE: This MIB object is for BladeCenter HT only." 
                         ::= { frontbezel 1}


     -- ********************************************************************************
     -- Environmental Monitor Thresholds
     -- ********************************************************************************
     monitorThresholds  OBJECT IDENTIFIER ::= { monitors 20 }

      

      -- ********************************************************************************
      -- Voltage Thresholds
      -- ********************************************************************************
      voltageThresholds  OBJECT IDENTIFIER ::= { monitorThresholds 2 }

       voltageThresholdsTable  OBJECT-TYPE
                             SYNTAX  SEQUENCE OF VoltageThresholdsEntry
                             MAX-ACCESS  not-accessible
                             STATUS  current -- was mandatory
                             DESCRIPTION
                             "Table of voltage threshold entries.
                             
                             NOTE: This MIB object is for BladeCenter only."
                             ::= {  voltageThresholds 1 }

       voltageThresholdsEntry  OBJECT-TYPE
                             SYNTAX VoltageThresholdsEntry
                             MAX-ACCESS  not-accessible
                             STATUS  current -- was mandatory
                             DESCRIPTION
                             "Voltage threshold entries.
                             
                             NOTE: This MIB object is for BladeCenter only."
                             INDEX { voltageThresholdEntryIndex }
                             ::= { voltageThresholdsTable 1 }

       VoltageThresholdsEntry ::= SEQUENCE {
                    voltageThresholdEntryIndex INTEGER,
                    voltageThresholdEntryName OCTET STRING,
                    voltageThresholdEntryCurrentValue OCTET STRING,
                    voltageThresholdEntryWarningHighValue OCTET STRING,
                    voltageThresholdEntryWarningResetHighValue OCTET STRING,
                    voltageThresholdEntryWarningLowValue OCTET STRING,
                    voltageThresholdEntryWarningResetLowValue OCTET STRING
                    }


       voltageThresholdEntryIndex  OBJECT-TYPE
                                 SYNTAX  INTEGER(0..255)
                                 MAX-ACCESS  read-only
                                 STATUS  current -- was mandatory
                                 DESCRIPTION
                                 "Index for voltage threshold entry."
                                 
                                 ::= { voltageThresholdsEntry 1 }

       voltageThresholdEntryName OBJECT-TYPE
                                 SYNTAX  OCTET STRING (SIZE(0..16))
                                 MAX-ACCESS  read-only
                                 STATUS  current -- was mandatory
                                 DESCRIPTION
                                 "Voltage threshold entry null terminated string that
                                 contains the power supply's name, for example '+5V'."
                                 
                                 ::= { voltageThresholdsEntry 2 }

       voltageThresholdEntryCurrentValue OBJECT-TYPE
                                   SYNTAX  OCTET STRING
                                   MAX-ACCESS  read-only
                                   STATUS  current -- was mandatory
                                   DESCRIPTION
                                   "Voltage reading expressed in Volts(V).
                                   An octet string expressed as 'sdd.dd Volts' where:
                                   s is the sign ('-' for negative or '+' for positive)
                                   d is a decimal digit or blank space for a leading zero.
                                   The string 'Not Readable!' indicates that the given monitor
                                   is not supported on this system."
                                   
                                   ::= { voltageThresholdsEntry 3 }

       voltageThresholdEntryWarningHighValue OBJECT-TYPE
                                   SYNTAX  OCTET STRING
                                   MAX-ACCESS  read-only
                                   STATUS  current -- was mandatory
                                   DESCRIPTION
                                   "Voltage threshold reading expressed in Volts(V).
                                   If the voltage rises above this value, a warning
                                   alert/event, if enabled, will be generated.
                                   An octet string expressed as 'sdd.dd Volts' where:
                                   s is the sign ('-' for negative or '+' for positive)
                                   d is a decimal digit or blank space for a leading zero.
                                   The string 'Not Readable!' indicates that the given monitor
                                   is not supported on this system."
                                   
                                   ::= { voltageThresholdsEntry 6 }

       voltageThresholdEntryWarningResetHighValue OBJECT-TYPE
                                   SYNTAX  OCTET STRING
                                   MAX-ACCESS  read-only
                                   STATUS  current -- was mandatory
                                   DESCRIPTION
                                   "Voltage threshold reading expressed in Volts(V).
                                   If the voltage rises above this value and
                                   if a warning alert/event had previously been
                                   created, then the alert/event will be reset.
                                   An octet string expressed as 'sdd.dd Volts' where:
                                   s is the sign ('-' for negative or '+' for positive)
                                   d is a decimal digit or blank space for a leading zero.
                                   The string 'Not Readable!' indicates that the given monitor
                                   is not supported on this system."
                                   
                                   ::= { voltageThresholdsEntry 7 }

       voltageThresholdEntryWarningLowValue OBJECT-TYPE
                                   SYNTAX  OCTET STRING
                                   MAX-ACCESS  read-only
                                   STATUS  current -- was mandatory
                                   DESCRIPTION
                                   "Voltage threshold reading expressed in Volts(V).
                                   If the voltage drops below this value, a warning
                                   alert/event, if enabled, will be generated.
                                   An octet string expressed as 'sdd.dd Volts' where:
                                   s is the sign ('-' for negative or '+' for positive)
                                   d is a decimal digit or blank space for a leading zero.
                                   The string 'Not Readable!' indicates that the given monitor
                                   is not supported on this system."
                                   
                                   ::= { voltageThresholdsEntry 10 }

       voltageThresholdEntryWarningResetLowValue OBJECT-TYPE
                                   SYNTAX  OCTET STRING
                                   MAX-ACCESS  read-only
                                   STATUS  current -- was mandatory
                                   DESCRIPTION
                                   "Voltage threshold reading expressed in Volts(V).
                                   If the voltage drops below this value and
                                   if a warning alert/event had previously been
                                   created, then the alert/event will be reset.
                                   An octet string expressed as 'sdd.dd Volts' where:
                                   s is the sign ('-' for negative or '+' for positive)
                                   d is a decimal digit or blank space for a leading zero.
                                   The string 'Not Readable!' indicates that the given monitor
                                   is not supported on this system."
                                   
                                   ::= { voltageThresholdsEntry 11 }

     -- ********************************************************************************
     -- Vital Product Data(VPD) information
     -- ********************************************************************************
     vpdInformation  OBJECT IDENTIFIER ::= { monitors 21 }

      -- ********************************************************************************
      -- System Firmware Level VPD
      -- ********************************************************************************
      
      -- ********************************************************************************
      -- Machine Level VPD
      -- ********************************************************************************
      chassisVpd OBJECT IDENTIFIER ::= { vpdInformation 1 }


       bladeCenterVpd OBJECT IDENTIFIER ::= { chassisVpd 1 }

        bladeCenterVpdMachineType OBJECT-TYPE
                      SYNTAX  OCTET STRING
                      MAX-ACCESS  read-write
                      STATUS  current -- was mandatory
                      DESCRIPTION
                      "Machine type VPD information (from System BIOS).  This field must be four 
                      alpha numeric characters."
                      ::= { bladeCenterVpd 1 }

        bladeCenterVpdMachineModel OBJECT-TYPE
                      SYNTAX  OCTET STRING
                      MAX-ACCESS  read-write
                      STATUS  current -- was mandatory
                      DESCRIPTION
                      "Machine model VPD information (from System BIOS).  This field  must be three 
                      alpha numeric characters."
                      ::= { bladeCenterVpd 2 }

        bladeCenterSerialNumber OBJECT-TYPE
                      SYNTAX  OCTET STRING
                      MAX-ACCESS  read-write
                      STATUS  current -- was mandatory
                      DESCRIPTION
                      "Machine serial number VPD information (from System BIOS).  This field must be 
                      seven alpha numeric characters."
                      ::= { bladeCenterVpd 3 }

        bladeCenterUUID OBJECT-TYPE
                      SYNTAX  OCTET STRING
                      MAX-ACCESS  read-write
                      STATUS  current -- was mandatory
                      DESCRIPTION
                      "Machine UUID (Universal Unique ID information) (from System BIOS).  This field 
                      must be 32 alpha numeric characters."
                      ::= { bladeCenterVpd 4 }

        bladeCenterManufacturingId OBJECT-TYPE
                      SYNTAX  OCTET STRING
                      MAX-ACCESS  read-only
                      STATUS  current -- was mandatory
                      DESCRIPTION
                      "Machine chassis manufacturing ID."
                      ::= { bladeCenterVpd 5 }

        bladeCenterHardwareRevision OBJECT-TYPE
                      SYNTAX  INTEGER
                      MAX-ACCESS  read-only
                      STATUS  current -- was mandatory
                      DESCRIPTION
                      "Machine chassis hardware revision.
                       If a hardware revision is programmed in the OEM VPD area for this component,
                       then the HardwareRevisionString version of this MIB object should be used."
                      ::= { bladeCenterVpd 6 }


        bladeCenterFruNumber OBJECT-TYPE
                      SYNTAX  OCTET STRING
                      MAX-ACCESS  read-only
                      STATUS  current -- was mandatory
                      DESCRIPTION
                      "Machine chassis FRU number."
                      ::= { bladeCenterVpd 7 }

        bladeCenterManufDate OBJECT-TYPE
                      SYNTAX  OCTET STRING
                      MAX-ACCESS  read-only
                      STATUS  current -- was mandatory
                      DESCRIPTION
                      "Machine chassis manufacture date."
                      ::= { bladeCenterVpd 8 }

        bladeCenterPartNumber OBJECT-TYPE
                      SYNTAX  OCTET STRING
                      MAX-ACCESS  read-only
                      STATUS  current -- was mandatory
                      DESCRIPTION
                      "Machine chassis part number."
                      ::= { bladeCenterVpd 9 }

        bladeCenterFruSerial OBJECT-TYPE
                      SYNTAX  OCTET STRING
                      MAX-ACCESS  read-only
                      STATUS  current -- was mandatory
                      DESCRIPTION
                      "Machine chassis FRU serial number."
                      ::= { bladeCenterVpd 10 }

        bladeCenterManufacturingIDNumber OBJECT-TYPE
                      SYNTAX  OCTET STRING
                      MAX-ACCESS  read-only
                      STATUS  current -- was mandatory
                      DESCRIPTION
                      "Machine chassis manufacturer ID Number."
                      ::= { bladeCenterVpd 11 }

        bladeCenterProductId OBJECT-TYPE
                      SYNTAX  OCTET STRING
                      MAX-ACCESS  read-only
                      STATUS  current -- was mandatory
                      DESCRIPTION
                      "Machine chassis product ID."
                      ::= { bladeCenterVpd 12 }

        bladeCenterSubManufacturerId OBJECT-TYPE
                      SYNTAX  OCTET STRING
                      MAX-ACCESS  read-only
                      STATUS  current -- was mandatory
                      DESCRIPTION
                      "Machine chassis subsystem manufacturer."
                      ::= { bladeCenterVpd 13 }

        bladeCenterClei OBJECT-TYPE
                      SYNTAX  OCTET STRING
                      MAX-ACCESS  read-only
                      STATUS  current -- was mandatory
                      DESCRIPTION
                      "Machine chassis Common Language Equipment Identification (CLEI)."
                      ::= { bladeCenterVpd 14 }

        bladeCenterDirectSerialAttach OBJECT-TYPE
                      SYNTAX  INTEGER {
                          false(0),
                          true(1)
                      }
                      MAX-ACCESS  read-only
                      STATUS  current -- was mandatory
                      DESCRIPTION
                      "Presence of the Direct Serial Attach Module.

                      NOTE: This MIB object is for BCS only."
                      ::= { bladeCenterVpd 15 }
                      
        bladeCenterHardwareRevisionString OBJECT-TYPE
                      SYNTAX  OCTET STRING
                      MAX-ACCESS  read-only
                      STATUS  current -- was mandatory
                      DESCRIPTION
                      "Machine chassis hardware revision in string format.
                       If a hardware revision is programmed in the OEM VPD area for this component,
                       then this MIB object should be used."
                      ::= { bladeCenterVpd 16 }

      -- ********************************************************************************
      -- Management Module Hardware VPD
      -- ********************************************************************************
      mmHardwareVpd OBJECT IDENTIFIER ::= { vpdInformation 2 }

      mmHardwareVpdTable OBJECT-TYPE
                    SYNTAX  SEQUENCE OF MmHardwareVpdEntry
                    MAX-ACCESS  not-accessible
                    STATUS  current -- was mandatory
                    DESCRIPTION
                    "Table of the management module hardware components.
                    For consistent results, view as a table and not as individual entries."
                    ::= { mmHardwareVpd 1 }

      mmHardwareVpdEntry OBJECT-TYPE
                    SYNTAX MmHardwareVpdEntry
                    MAX-ACCESS  not-accessible
                    STATUS  current -- was mandatory
                    DESCRIPTION
                    "Management module hardware VPD entry.
                    For consistent results, view as a table and not as individual entries."
                    INDEX { mmHardwareVpdIndex }
                    ::= { mmHardwareVpdTable 1 }

      MmHardwareVpdEntry ::= SEQUENCE {
                  mmHardwareVpdIndex INTEGER,
                  mmHardwareVpdBayNumber OCTET STRING,
                  mmHardwareVpdManufacturingId OCTET STRING,
                  mmHardwareVpdFruNumber OCTET STRING,
                  mmHardwareVpdHardwareRevision INTEGER,
                  mmHardwareVpdUuid OCTET STRING,
                  mmHardwareVpdManufDate OCTET STRING,
                  mmHardwareVpdPartNumber OCTET STRING,
                  mmHardwareVpdFruSerial OCTET STRING,
                  mmHardwareVpdManufacturingIDNumber OCTET STRING,
                  mmHardwareVpdProductId OCTET STRING,
                  mmHardwareVpdSubManufacturerId OCTET STRING,
                  mmHardwareVpdClei OCTET STRING,
                  mmHardwareVpdHardwareRevisionString OCTET STRING
                  }

      mmHardwareVpdIndex  OBJECT-TYPE
                  SYNTAX  Integer32 (0..2147483647) -- was INTEGER
                  MAX-ACCESS  read-only
                  STATUS  current -- was mandatory
                  DESCRIPTION
                  "Management module hardware VPD index.
                  For consistent results, view as a table and not as individual entries."
                  ::= { mmHardwareVpdEntry 1 }

      mmHardwareVpdBayNumber  OBJECT-TYPE
                  SYNTAX  OCTET STRING
                  MAX-ACCESS  read-only
                  STATUS  current -- was mandatory
                  DESCRIPTION
                  "Management module hardware VPD Bay number.
                  For consistent results, view as a table and not as individual entries."
                  ::= { mmHardwareVpdEntry 2 }

      mmHardwareVpdManufacturingId  OBJECT-TYPE
                  SYNTAX  OCTET STRING
                  MAX-ACCESS  read-only
                  STATUS  current -- was mandatory
                  DESCRIPTION
                  "Management module hardware VPD manufacturing ID.
                  For consistent results, view as a table and not as individual entries."
                  ::= { mmHardwareVpdEntry 3 }
      mmHardwareVpdFruNumber  OBJECT-TYPE
                  SYNTAX  OCTET STRING
                  MAX-ACCESS  read-only
                  STATUS  current -- was mandatory
                  DESCRIPTION
                  "Management module hardware VPD FRU number.
                  For consistent results, view as a table and not as individual entries."
                  ::= { mmHardwareVpdEntry 4 }


      mmHardwareVpdHardwareRevision  OBJECT-TYPE
                  SYNTAX  INTEGER
                  MAX-ACCESS  read-only
                  STATUS  current -- was mandatory
                  DESCRIPTION
                  "Management module hardware VPD hardware revision.
                  For consistent results, view as a table and not as individual entries.
                  If a hardware revision is programmed in the OEM VPD area for this component,
                  then the HardwareRevisionString version of this MIB object should be used."
                  ::= { mmHardwareVpdEntry 5 }

      mmHardwareVpdUuid  OBJECT-TYPE
                  SYNTAX  OCTET STRING
                  MAX-ACCESS  read-only
                  STATUS  current -- was mandatory
                  DESCRIPTION
                  "Management module hardware VPD UUID.
                  For consistent results, view as a table and not as individual entries."
                  ::= { mmHardwareVpdEntry 6 }

      mmHardwareVpdManufDate  OBJECT-TYPE
                  SYNTAX  OCTET STRING
                  MAX-ACCESS  read-only
                  STATUS  current -- was mandatory
                  DESCRIPTION
                  "Management module hardware VPD manufacture date.
                  For consistent results, view as a table and not as individual entries."
                  ::= { mmHardwareVpdEntry 7 }

      mmHardwareVpdPartNumber  OBJECT-TYPE
                  SYNTAX  OCTET STRING
                  MAX-ACCESS  read-only
                  STATUS  current -- was mandatory
                  DESCRIPTION
                  "Management module hardware VPD Part number.
                  For consistent results, view as a table and not as individual entries."
                  ::= { mmHardwareVpdEntry 8 }

      mmHardwareVpdFruSerial  OBJECT-TYPE
                  SYNTAX  OCTET STRING
                  MAX-ACCESS  read-only
                  STATUS  current -- was mandatory
                  DESCRIPTION
                  "Management module hardware VPD FRU serial number.
                  For consistent results, view as a table and not as individual entries."
                  ::= { mmHardwareVpdEntry 9 }

      mmHardwareVpdManufacturingIDNumber  OBJECT-TYPE
                  SYNTAX  OCTET STRING
                  MAX-ACCESS  read-only
                  STATUS  current -- was mandatory
                  DESCRIPTION
                  "Management module hardware VPD manufacturer ID Number.
                  For consistent results, view as a table and not as individual entries."
                  ::= { mmHardwareVpdEntry 10 }

      mmHardwareVpdProductId  OBJECT-TYPE
                  SYNTAX  OCTET STRING
                  MAX-ACCESS  read-only
                  STATUS  current -- was mandatory
                  DESCRIPTION
                  "Management module hardware VPD product ID.
                  For consistent results, view as a table and not as individual entries."
                  ::= { mmHardwareVpdEntry 11 }

      mmHardwareVpdSubManufacturerId  OBJECT-TYPE
                  SYNTAX  OCTET STRING
                  MAX-ACCESS  read-only
                  STATUS  current -- was mandatory
                  DESCRIPTION
                  "Management module hardware VPD subsystem manufacturer.
                  For consistent results, view as a table and not as individual entries."
                  ::= { mmHardwareVpdEntry 12 }

      mmHardwareVpdClei  OBJECT-TYPE
                  SYNTAX  OCTET STRING
                  MAX-ACCESS  read-only
                  STATUS  current -- was mandatory
                  DESCRIPTION
                  "Management module hardware VPD Common
                  Language Equipment Identification (CLEI).
                  For consistent results, view as a table and not as individual entries."
                  ::= { mmHardwareVpdEntry 13 }
                  
      mmHardwareVpdHardwareRevisionString  OBJECT-TYPE
                  SYNTAX  OCTET STRING
                  MAX-ACCESS  read-only
                  STATUS  current -- was mandatory
                  DESCRIPTION
                  "Management module hardware VPD hardware revision in string format.
                  For consistent results, view as a table and not as individual entries.
                  If a hardware revision is programmed in the OEM VPD area for this component,
                  then this MIB object should be used."
                  ::= { mmHardwareVpdEntry 14 }
                  
      -- ********************************************************************************
      -- Management Module Interposer Hardware VPD
      -- ********************************************************************************

      mmInpHardwareVpdTable OBJECT-TYPE
                    SYNTAX  SEQUENCE OF MmInpHardwareVpdEntry
                    MAX-ACCESS  not-accessible
                    STATUS  current -- was mandatory
                    DESCRIPTION
                    "Table of the management module interposer hardware components.
                    For consistent results, view as a table and not as individual entries.
                              
                    NOTE: This MIB object is for BladeCenter HT only." 
                    ::= { mmHardwareVpd 2 }

      mmInpHardwareVpdEntry OBJECT-TYPE
                    SYNTAX MmInpHardwareVpdEntry
                    MAX-ACCESS  not-accessible
                    STATUS  current -- was mandatory
                    DESCRIPTION
                    "Management module Interposer hardware VPD entry.
                    For consistent results, view as a table and not as individual entries.
                              
                    NOTE: This MIB object is for BladeCenter HT only." 
                    INDEX { mmInpHardwareVpdIndex }
                    ::= { mmInpHardwareVpdTable 1 }

      MmInpHardwareVpdEntry ::= SEQUENCE {
                  mmInpHardwareVpdIndex INTEGER,
                  mmInpHardwareVpdBayNumber OCTET STRING,
                  mmInpHardwareVpdManufacturingId OCTET STRING,
                  mmInpHardwareVpdFruNumber OCTET STRING,
                  mmInpHardwareVpdHardwareRevision INTEGER,
                  mmInpHardwareVpdUuid OCTET STRING,
                  mmInpHardwareVpdManufDate OCTET STRING,
                  mmInpHardwareVpdPartNumber OCTET STRING,
                  mmInpHardwareVpdFruSerial OCTET STRING,
                  mmInpHardwareVpdManufacturingIDNumber OCTET STRING,
                  mmInpHardwareVpdProductId OCTET STRING,
                  mmInpHardwareVpdSubManufacturerId OCTET STRING,
                  mmInpHardwareVpdClei OCTET STRING,
                  mmInpHardwareVpdHardwareRevisionString OCTET STRING
                  }

      mmInpHardwareVpdIndex  OBJECT-TYPE
                  SYNTAX  Integer32 (0..2147483647) -- was INTEGER
                  MAX-ACCESS  read-only
                  STATUS  current -- was mandatory
                  DESCRIPTION
                  "Management module Interposer hardware VPD index.
                  For consistent results, view as a table and not as individual entries.
                              
                  NOTE: This MIB object is for BladeCenter HT only." 
                  ::= { mmInpHardwareVpdEntry 1 }

      mmInpHardwareVpdBayNumber  OBJECT-TYPE
                  SYNTAX  OCTET STRING
                  MAX-ACCESS  read-only
                  STATUS  current -- was mandatory
                  DESCRIPTION
                  "Management module Interposer hardware VPD Bay number.
                  For consistent results, view as a table and not as individual entries.
                              
                  NOTE: This MIB object is for BladeCenter HT only." 
                  ::= { mmInpHardwareVpdEntry 2 }

      mmInpHardwareVpdManufacturingId  OBJECT-TYPE
                  SYNTAX  OCTET STRING
                  MAX-ACCESS  read-only
                  STATUS  current -- was mandatory
                  DESCRIPTION
                  "Management module Interposer hardware VPD manufacturing ID.
                  For consistent results, view as a table and not as individual entries.
                              
                  NOTE: This MIB object is for BladeCenter HT only." 
                  ::= { mmInpHardwareVpdEntry 3 }

      mmInpHardwareVpdFruNumber  OBJECT-TYPE
                  SYNTAX  OCTET STRING
                  MAX-ACCESS  read-only
                  STATUS  current -- was mandatory
                  DESCRIPTION
                  "Management module Interposer hardware VPD FRU number.
                  For consistent results, view as a table and not as individual entries.
                              
                  NOTE: This MIB object is for BladeCenter HT only." 
                  ::= { mmInpHardwareVpdEntry 4 }


      mmInpHardwareVpdHardwareRevision  OBJECT-TYPE
                  SYNTAX  INTEGER
                  MAX-ACCESS  read-only
                  STATUS  current -- was mandatory
                  DESCRIPTION
                  "Management module Interposer hardware VPD hardware revision.
                  For consistent results, view as a table and not as individual entries.
                              
                  NOTE: This MIB object is for BladeCenter HT only. 
                        If a hardware revision is programmed in the OEM VPD area for this component,
                        then the HardwareRevisionString version of this MIB object should be used."
                  ::= { mmInpHardwareVpdEntry 5 }

      mmInpHardwareVpdUuid  OBJECT-TYPE
                  SYNTAX  OCTET STRING
                  MAX-ACCESS  read-only
                  STATUS  current -- was mandatory
                  DESCRIPTION
                  "Management module Interposer hardware VPD UUID.
                  For consistent results, view as a table and not as individual entries.
                              
                  NOTE: This MIB object is for BladeCenter HT only." 
                  ::= { mmInpHardwareVpdEntry 6 }

      mmInpHardwareVpdManufDate  OBJECT-TYPE
                  SYNTAX  OCTET STRING
                  MAX-ACCESS  read-only
                  STATUS  current -- was mandatory
                  DESCRIPTION
                  "Management module Interposer hardware VPD manufacture date.
                  For consistent results, view as a table and not as individual entries.
                              
                  NOTE: This MIB object is for BladeCenter HT only." 
                  ::= { mmInpHardwareVpdEntry 7 }

      mmInpHardwareVpdPartNumber  OBJECT-TYPE
                  SYNTAX  OCTET STRING
                  MAX-ACCESS  read-only
                  STATUS  current -- was mandatory
                  DESCRIPTION
                  "Management module Interposer hardware VPD Part number.
                  For consistent results, view as a table and not as individual entries.
                              
                  NOTE: This MIB object is for BladeCenter HT only." 
                  ::= { mmInpHardwareVpdEntry 8 }

      mmInpHardwareVpdFruSerial  OBJECT-TYPE
                  SYNTAX  OCTET STRING
                  MAX-ACCESS  read-only
                  STATUS  current -- was mandatory
                  DESCRIPTION
                  "Management module Interposer hardware VPD FRU serial number.
                  For consistent results, view as a table and not as individual entries.
                              
                  NOTE: This MIB object is for BladeCenter HT only." 
                  ::= { mmInpHardwareVpdEntry 9 } 
                  
      mmInpHardwareVpdManufacturingIDNumber  OBJECT-TYPE
                  SYNTAX  OCTET STRING
                  MAX-ACCESS  read-only
                  STATUS  current -- was mandatory
                  DESCRIPTION
                  "Management module Interposer hardware VPD manufacturer ID Number.
                  For consistent results, view as a table and not as individual entries."
                  ::= { mmInpHardwareVpdEntry 10 }

      mmInpHardwareVpdProductId  OBJECT-TYPE
                  SYNTAX  OCTET STRING
                  MAX-ACCESS  read-only
                  STATUS  current -- was mandatory
                  DESCRIPTION
                  "Management module Interposer hardware VPD product ID.
                  For consistent results, view as a table and not as individual entries."
                  ::= { mmInpHardwareVpdEntry 11 }

      mmInpHardwareVpdSubManufacturerId  OBJECT-TYPE
                  SYNTAX  OCTET STRING
                  MAX-ACCESS  read-only
                  STATUS  current -- was mandatory
                  DESCRIPTION
                  "Management module Interposer hardware VPD subsystem manufacturer.
                  For consistent results, view as a table and not as individual entries."
                  ::= { mmInpHardwareVpdEntry 12 }

      mmInpHardwareVpdClei  OBJECT-TYPE
                  SYNTAX  OCTET STRING
                  MAX-ACCESS  read-only
                  STATUS  current -- was mandatory
                  DESCRIPTION
                  "Management module Interposer hardware VPD Common 
                  Language Equipment Identification (CLEI).
                  For consistent results, view as a table and not as individual entries."
                  ::= { mmInpHardwareVpdEntry 13 }           

      mmInpHardwareVpdHardwareRevisionString  OBJECT-TYPE
                  SYNTAX  OCTET STRING
                  MAX-ACCESS  read-only
                  STATUS  current -- was mandatory
                  DESCRIPTION
                  "Management module Interposer hardware VPD hardware revision in string format.
                  For consistent results, view as a table and not as individual entries.
                              
                  NOTE: This MIB object is for BladeCenter HT only. 
                  
                        If a hardware revision is programmed in the OEM VPD area for this component,
                        then this version of this MIB object should be used."
                  ::= { mmInpHardwareVpdEntry 14 }

      -- ********************************************************************************
      -- System Firmware Level VPD
      -- ********************************************************************************
      mmFirmwareVpd OBJECT IDENTIFIER ::= { vpdInformation 3 }

       -- ********************************************************************************
       -- MM Firmware VPD
       -- ********************************************************************************
       mmMainApplVpdTable OBJECT-TYPE
                     SYNTAX  SEQUENCE OF MmMainApplVpdEntry
                     MAX-ACCESS  not-accessible
                     STATUS  current -- was mandatory
                     DESCRIPTION
                     "Table of MM Firmware VPD."
                     ::= { mmFirmwareVpd 1 }

       mmMainApplVpdEntry OBJECT-TYPE
                     SYNTAX MmMainApplVpdEntry
                     MAX-ACCESS  not-accessible
                     STATUS  current -- was mandatory
                     DESCRIPTION
                     "MM Firmware VPD entry."
                     INDEX { mmMainApplVpdIndex }
                     ::= { mmMainApplVpdTable 1 }


       MmMainApplVpdEntry ::= SEQUENCE {
                   mmMainApplVpdIndex INTEGER,
                   mmMainApplVpdName OCTET STRING,
                   mmMainApplVpdBuildId OCTET STRING,
                   mmMainApplVpdRevisonNumber OCTET STRING,
                   mmMainApplVpdFilename OCTET STRING,
                   mmMainApplVpdBuildDate OCTET STRING
                   }


       mmMainApplVpdIndex  OBJECT-TYPE
                   SYNTAX  Integer32 (0..2147483647) -- was INTEGER
                   MAX-ACCESS  read-only
                   STATUS  current -- was mandatory
                   DESCRIPTION
                   "Firmware VPD index."
                   ::= { mmMainApplVpdEntry 1 }

       mmMainApplVpdName  OBJECT-TYPE
                   SYNTAX  OCTET STRING
                   MAX-ACCESS  read-only
                   STATUS  current -- was mandatory
                   DESCRIPTION
                   "Firmware VPD name description."
                   ::= { mmMainApplVpdEntry 2 }

       mmMainApplVpdBuildId  OBJECT-TYPE
                   SYNTAX  OCTET STRING
                   MAX-ACCESS  read-only
                   STATUS  current -- was mandatory
                   DESCRIPTION
                   "Firmware VPD build identification."
                   ::= { mmMainApplVpdEntry 3 }

       mmMainApplVpdRevisonNumber  OBJECT-TYPE
                   SYNTAX  OCTET STRING
                   MAX-ACCESS  read-only
                   STATUS  current -- was mandatory
                   DESCRIPTION
                   "Firmware VPD revision number."
                   ::= { mmMainApplVpdEntry 4 }

       mmMainApplVpdFilename  OBJECT-TYPE
                   SYNTAX  OCTET STRING
                   MAX-ACCESS  read-only
                   STATUS  current -- was mandatory
                   DESCRIPTION
                   "Firmware VPD file name."
                   ::= { mmMainApplVpdEntry 5 }

       mmMainApplVpdBuildDate  OBJECT-TYPE
                   SYNTAX  OCTET STRING
                   MAX-ACCESS  read-only
                   STATUS  current -- was mandatory
                   DESCRIPTION
                   "Firmware VPD build date."
                   ::= { mmMainApplVpdEntry 6 }

       -- ********************************************************************************
       -- MM Firmware VPD
       -- ********************************************************************************
       mmBootROMVpdTable OBJECT-TYPE
                     SYNTAX  SEQUENCE OF MmBootROMVpdEntry
                     MAX-ACCESS  not-accessible
                     STATUS  current -- was mandatory
                     DESCRIPTION
                     "Table of MM Firmware VPD.
                     
                     NOTE: This MIB object is for MM only."
                     ::= { mmFirmwareVpd 2 }

       mmBootROMVpdEntry OBJECT-TYPE
                     SYNTAX MmBootROMVpdEntry
                     MAX-ACCESS  not-accessible
                     STATUS  current -- was mandatory
                     DESCRIPTION
                     "MM Firmware VPD entry.
                     
                     NOTE: This MIB object is for MM only."
                     INDEX { mmBootROMVpdIndex }
                     ::= { mmBootROMVpdTable 1 }


       MmBootROMVpdEntry ::= SEQUENCE {
                   mmBootROMVpdIndex INTEGER,
                   mmBootROMVpdName OCTET STRING,
                   mmBootROMVpdBuildId OCTET STRING,
                   mmBootROMVpdRevisonNumber OCTET STRING,
                   mmBootROMVpdFilename OCTET STRING,
                   mmBootROMVpdBuildDate OCTET STRING
                   }


       mmBootROMVpdIndex  OBJECT-TYPE
                   SYNTAX  Integer32 (0..2147483647) -- was INTEGER
                   MAX-ACCESS  read-only
                   STATUS  current -- was mandatory
                   DESCRIPTION
                   "Firmware VPD index.
                    
                   NOTE: This MIB object is for MM only."
                   ::= { mmBootROMVpdEntry 1 }

       mmBootROMVpdName  OBJECT-TYPE
                   SYNTAX  OCTET STRING
                   MAX-ACCESS  read-only
                   STATUS  current -- was mandatory
                   DESCRIPTION
                   "Firmware VPD name description.
                   
                   NOTE: This MIB object is for MM only."
                   ::= { mmBootROMVpdEntry 2 }

       mmBootROMVpdBuildId  OBJECT-TYPE
                   SYNTAX  OCTET STRING
                   MAX-ACCESS  read-only
                   STATUS  current -- was mandatory
                   DESCRIPTION
                   "Firmware VPD build identification.
                   
                   NOTE: This MIB object is for MM only."
                   ::= { mmBootROMVpdEntry 3 }

       mmBootROMVpdRevisonNumber  OBJECT-TYPE
                   SYNTAX  OCTET STRING
                   MAX-ACCESS  read-only
                   STATUS  current -- was mandatory
                   DESCRIPTION
                   "Firmware VPD revision number.
                   
                   NOTE: This MIB object is for MM only."
                   ::= { mmBootROMVpdEntry 4 }

       mmBootROMVpdFilename  OBJECT-TYPE
                   SYNTAX  OCTET STRING
                   MAX-ACCESS  read-only
                   STATUS  current -- was mandatory
                   DESCRIPTION
                   "Firmware VPD file name.
                   
                   NOTE: This MIB object is for MM only."
                   ::= { mmBootROMVpdEntry 5 }

       mmBootROMVpdBuildDate  OBJECT-TYPE
                   SYNTAX  OCTET STRING
                   MAX-ACCESS  read-only
                   STATUS  current -- was mandatory
                   DESCRIPTION
                   "Firmware VPD build date.
                   
                   NOTE: This MIB object is for MM only."
                   ::= { mmBootROMVpdEntry 6 }


       -- ******************************************************************************** 
       -- MM Firmware VPD
       -- ********************************************************************************
       mmRemoteControlVpdTable OBJECT-TYPE
                     SYNTAX  SEQUENCE OF MmRemoteControlVpdEntry
                     MAX-ACCESS  not-accessible
                     STATUS  current -- was mandatory
                     DESCRIPTION
                     "Table of MM Firmware VPD. 
                     NOTE: This MIB object is for MM only."
                     ::= { mmFirmwareVpd 3 }

       mmRemoteControlVpdEntry OBJECT-TYPE
                     SYNTAX MmRemoteControlVpdEntry
                     MAX-ACCESS  not-accessible
                     STATUS  current -- was mandatory
                     DESCRIPTION
                     "MM Firmware VPD entry."
                     INDEX { mmRemoteControlVpdIndex }
                     ::= { mmRemoteControlVpdTable 1 }


       MmRemoteControlVpdEntry ::= SEQUENCE {
                   mmRemoteControlVpdIndex INTEGER,
                   mmRemoteControlVpdName OCTET STRING,
                   mmRemoteControlVpdBuildId OCTET STRING,
                   mmRemoteControlVpdRevisonNumber OCTET STRING,
                   mmRemoteControlVpdFilename OCTET STRING,
                   mmRemoteControlVpdBuildDate OCTET STRING
                   }


       mmRemoteControlVpdIndex  OBJECT-TYPE
                   SYNTAX  Integer32 (0..2147483647) -- was INTEGER
                   MAX-ACCESS  read-only
                   STATUS  current -- was mandatory
                   DESCRIPTION
                   "Firmware VPD index."
                   ::= { mmRemoteControlVpdEntry 1 }

       mmRemoteControlVpdName  OBJECT-TYPE
                   SYNTAX  OCTET STRING
                   MAX-ACCESS  read-only
                   STATUS  current -- was mandatory
                   DESCRIPTION
                   "Firmware VPD name description."
                   ::= { mmRemoteControlVpdEntry 2 }

       mmRemoteControlVpdBuildId  OBJECT-TYPE
                   SYNTAX  OCTET STRING
                   MAX-ACCESS  read-only
                   STATUS  current -- was mandatory
                   DESCRIPTION
                   "Firmware VPD build identification."
                   ::= { mmRemoteControlVpdEntry 3 }

       mmRemoteControlVpdRevisonNumber  OBJECT-TYPE
                   SYNTAX  OCTET STRING
                   MAX-ACCESS  read-only
                   STATUS  current -- was mandatory
                   DESCRIPTION
                   "Firmware VPD revision number."
                   ::= { mmRemoteControlVpdEntry 4 }

       mmRemoteControlVpdFilename  OBJECT-TYPE
                   SYNTAX  OCTET STRING
                   MAX-ACCESS  read-only
                   STATUS  current -- was mandatory
                   DESCRIPTION
                   "Firmware VPD file name."
                   ::= { mmRemoteControlVpdEntry 5 }

       mmRemoteControlVpdBuildDate  OBJECT-TYPE
                   SYNTAX  OCTET STRING
                   MAX-ACCESS  read-only
                   STATUS  current -- was mandatory
                   DESCRIPTION
                   "Firmware VPD build date."
                   ::= { mmRemoteControlVpdEntry 6 }


       -- ********************************************************************************
       -- MM Firmware VPD
       -- ********************************************************************************
       mmPS2toUSBConvVpdTable OBJECT-TYPE
                     SYNTAX  SEQUENCE OF MmPS2toUSBConvVpdEntry
                     MAX-ACCESS  not-accessible
                     STATUS  current -- was mandatory
                     DESCRIPTION
                     "Table of MM Firmware VPD. 
                     NOTE: This MIB object is for MM only."
                     ::= { mmFirmwareVpd 4 }

       mmPS2toUSBConvVpdEntry OBJECT-TYPE
                     SYNTAX MmPS2toUSBConvVpdEntry
                     MAX-ACCESS  not-accessible
                     STATUS  current -- was mandatory
                     DESCRIPTION
                     "MM Firmware VPD entry."
                     INDEX { mmPS2toUSBConvVpdIndex }
                     ::= { mmPS2toUSBConvVpdTable 1 }


       MmPS2toUSBConvVpdEntry ::= SEQUENCE {
                   mmPS2toUSBConvVpdIndex INTEGER,
                   mmPS2toUSBConvVpdName OCTET STRING,
                   mmPS2toUSBConvVpdBuildId OCTET STRING,
                   mmPS2toUSBConvVpdRevisonNumber OCTET STRING,
                   mmPS2toUSBConvVpdFilename OCTET STRING,
                   mmPS2toUSBConvVpdBuildDate OCTET STRING
                   }


       mmPS2toUSBConvVpdIndex  OBJECT-TYPE
                   SYNTAX  Integer32 (0..2147483647) -- was INTEGER
                   MAX-ACCESS  read-only
                   STATUS  current -- was mandatory
                   DESCRIPTION
                   "Firmware VPD index."
                   ::= { mmPS2toUSBConvVpdEntry 1 }

       mmPS2toUSBConvVpdName  OBJECT-TYPE
                   SYNTAX  OCTET STRING
                   MAX-ACCESS  read-only
                   STATUS  current -- was mandatory
                   DESCRIPTION
                   "Firmware VPD name description."
                   ::= { mmPS2toUSBConvVpdEntry 2 }

       mmPS2toUSBConvVpdBuildId  OBJECT-TYPE
                   SYNTAX  OCTET STRING
                   MAX-ACCESS  read-only
                   STATUS  current -- was mandatory
                   DESCRIPTION
                   "Firmware VPD build identification."
                   ::= { mmPS2toUSBConvVpdEntry 3 }

       mmPS2toUSBConvVpdRevisonNumber  OBJECT-TYPE
                   SYNTAX  OCTET STRING
                   MAX-ACCESS  read-only
                   STATUS  current -- was mandatory
                   DESCRIPTION
                   "Firmware VPD revision number."
                   ::= { mmPS2toUSBConvVpdEntry 4 }

       mmPS2toUSBConvVpdFilename  OBJECT-TYPE
                   SYNTAX  OCTET STRING
                   MAX-ACCESS  read-only
                   STATUS  current -- was mandatory
                   DESCRIPTION
                   "Firmware VPD file name."
                   ::= { mmPS2toUSBConvVpdEntry 5 }

       mmPS2toUSBConvVpdBuildDate  OBJECT-TYPE
                   SYNTAX  OCTET STRING
                   MAX-ACCESS  read-only
                   STATUS  current -- was mandatory
                   DESCRIPTION
                   "Firmware VPD build date."
                   ::= { mmPS2toUSBConvVpdEntry 6 }


       -- ********************************************************************************
       -- MM Firmware VPD
       -- ********************************************************************************
       mmToUSBIntfVpdTable OBJECT-TYPE
                     SYNTAX  SEQUENCE OF MmToUSBIntfVpdEntry
                     MAX-ACCESS  not-accessible
                     STATUS  current -- was mandatory
                     DESCRIPTION
                     "Table of MM Firmware VPD. 
                     NOTE: This MIB object is for MM only."
                     ::= { mmFirmwareVpd 5 }

       mmToUSBIntfVpdEntry OBJECT-TYPE
                     SYNTAX MmToUSBIntfVpdEntry
                     MAX-ACCESS  not-accessible
                     STATUS  current -- was mandatory
                     DESCRIPTION
                     "MM Firmware VPD entry."
                     INDEX { mmToUSBIntfVpdIndex }
                     ::= { mmToUSBIntfVpdTable 1 }


       MmToUSBIntfVpdEntry ::= SEQUENCE {
                   mmToUSBIntfVpdIndex INTEGER,
                   mmToUSBIntfVpdName OCTET STRING,
                   mmToUSBIntfVpdBuildId OCTET STRING,
                   mmToUSBIntfVpdRevisonNumber OCTET STRING,
                   mmToUSBIntfVpdFilename OCTET STRING,
                   mmToUSBIntfVpdBuildDate OCTET STRING
                   }


       mmToUSBIntfVpdIndex  OBJECT-TYPE
                   SYNTAX  Integer32 (0..2147483647) -- was INTEGER
                   MAX-ACCESS  read-only
                   STATUS  current -- was mandatory
                   DESCRIPTION
                   "Firmware VPD index."
                   ::= { mmToUSBIntfVpdEntry 1 }

       mmToUSBIntfVpdName  OBJECT-TYPE
                   SYNTAX  OCTET STRING
                   MAX-ACCESS  read-only
                   STATUS  current -- was mandatory
                   DESCRIPTION
                   "Firmware VPD name description."
                   ::= { mmToUSBIntfVpdEntry 2 }

       mmToUSBIntfVpdBuildId  OBJECT-TYPE
                   SYNTAX  OCTET STRING
                   MAX-ACCESS  read-only
                   STATUS  current -- was mandatory
                   DESCRIPTION
                   "Firmware VPD build identification."
                   ::= { mmToUSBIntfVpdEntry 3 }

       mmToUSBIntfVpdRevisonNumber  OBJECT-TYPE
                   SYNTAX  OCTET STRING
                   MAX-ACCESS  read-only
                   STATUS  current -- was mandatory
                   DESCRIPTION
                   "Firmware VPD revision number."
                   ::= { mmToUSBIntfVpdEntry 4 }

       mmToUSBIntfVpdFilename  OBJECT-TYPE
                   SYNTAX  OCTET STRING
                   MAX-ACCESS  read-only
                   STATUS  current -- was mandatory
                   DESCRIPTION
                   "Firmware VPD file name."
                   ::= { mmToUSBIntfVpdEntry 5 }

       mmToUSBIntfVpdBuildDate  OBJECT-TYPE
                   SYNTAX  OCTET STRING
                   MAX-ACCESS  read-only
                   STATUS  current -- was mandatory
                   DESCRIPTION
                   "Firmware VPD build date."
                   ::= { mmToUSBIntfVpdEntry 6 }

      -- ********************************************************************************
      -- System Component Level VPD Activity log
      -- ********************************************************************************
      inventoryManagementActivityVpdTable OBJECT-TYPE
                    SYNTAX  SEQUENCE OF InventoryManagementActivityVpdEntry
                    MAX-ACCESS  not-accessible
                    STATUS  current -- was mandatory
                    DESCRIPTION
                    "Table of system component hardware VPD activity log.
                    For consistent results, view as a table and not as individual entries."
                    ::= { vpdInformation 22 }

      inventoryManagementActivityVpdEntry OBJECT-TYPE
                    SYNTAX InventoryManagementActivityVpdEntry
                    MAX-ACCESS  not-accessible
                    STATUS  current -- was mandatory
                    DESCRIPTION
                    "System component hardware VPD activity log entry.
                    For consistent results, view as a table and not as individual entries."
                    INDEX { componentLevelActivityVpdIndex }
                    ::= { inventoryManagementActivityVpdTable 1 }

      InventoryManagementActivityVpdEntry ::= SEQUENCE {
                  componentLevelActivityVpdIndex INTEGER,
                  componentLevelActivityVpdFruNumber OCTET STRING,
                  componentLevelActivityVpdSerialNumber OCTET STRING,
                  componentLevelActivityVpdManufacturingId OCTET STRING,
                  componentLevelActivityVpdBayNumber OCTET STRING,
                  componentLevelActivityVpdAction OCTET STRING,
                  componentLevelActivityVpdTimestamp OCTET STRING
                  }

      componentLevelActivityVpdIndex  OBJECT-TYPE
                  SYNTAX  Integer32 (0..2147483647) -- was INTEGER
                  MAX-ACCESS  read-only
                  STATUS  current -- was mandatory
                  DESCRIPTION
                  "System component level VPD activity log index.
                  For consistent results, view as a table and not as individual entries."
                  ::= { inventoryManagementActivityVpdEntry 1 }

      componentLevelActivityVpdFruNumber  OBJECT-TYPE
                  SYNTAX  OCTET STRING
                  MAX-ACCESS  read-only
                  STATUS  current -- was mandatory
                  DESCRIPTION
                  "System component level VPD activity log FRU number.
                  For consistent results, view as a table and not as individual entries."
                  ::= { inventoryManagementActivityVpdEntry 2 }

      componentLevelActivityVpdSerialNumber  OBJECT-TYPE
                  SYNTAX  OCTET STRING
                  MAX-ACCESS  read-only
                  STATUS  current -- was mandatory
                  DESCRIPTION
                  "System component level VPD activity log serial number.
                  For consistent results, view as a table and not as individual entries."
                  ::= { inventoryManagementActivityVpdEntry 3 }

      componentLevelActivityVpdManufacturingId  OBJECT-TYPE
                  SYNTAX  OCTET STRING
                  MAX-ACCESS  read-only
                  STATUS  current -- was mandatory
                  DESCRIPTION
                  "System component level VPD activity log manufacturing ID.
                  For consistent results, view as a table and not as individual entries."
                  ::= { inventoryManagementActivityVpdEntry 4 }

      componentLevelActivityVpdBayNumber  OBJECT-TYPE
                  SYNTAX  OCTET STRING
                  MAX-ACCESS  read-only
                  STATUS  current -- was mandatory
                  DESCRIPTION
                  "System component level VPD activity log Bay number.
                  For consistent results, view as a table and not as individual entries."
                  ::= { inventoryManagementActivityVpdEntry 5 }

      componentLevelActivityVpdAction  OBJECT-TYPE
                  SYNTAX  OCTET STRING
                  MAX-ACCESS  read-only
                  STATUS  current -- was mandatory
                  DESCRIPTION
                  "System component level VPD activity log action (added/removed).
                  For consistent results, view as a table and not as individual entries."
                  ::= {inventoryManagementActivityVpdEntry 9 }

      componentLevelActivityVpdTimestamp  OBJECT-TYPE
                  SYNTAX  OCTET STRING
                  MAX-ACCESS  read-only
                  STATUS  current -- was mandatory
                  DESCRIPTION
                  "System component level VPD activity log timestamp.
                  For consistent results, view as a table and not as individual entries."
                  ::= { inventoryManagementActivityVpdEntry 10 }
                  
      -- ********************************************************************************
      -- Blade Hardware VPD
      -- ********************************************************************************
      bladeHardwareVpd OBJECT IDENTIFIER ::= { vpdInformation 4 }

      bladeHardwareVpdTable OBJECT-TYPE
                    SYNTAX  SEQUENCE OF BladeHardwareVpdEntry
                    MAX-ACCESS  not-accessible
                    STATUS  current -- was mandatory
                    DESCRIPTION
                    "Table of VPD information for the blade hardware components.
                    For consistent results, view as a table and not as individual entries."
                    ::= { bladeHardwareVpd 1 }

      bladeHardwareVpdEntry OBJECT-TYPE
                    SYNTAX BladeHardwareVpdEntry
                    MAX-ACCESS  not-accessible
                    STATUS  current -- was mandatory
                    DESCRIPTION
                    "Blade hardware VPD entry.
                    For consistent results, view as a table and not as individual entries."
                    INDEX { bladeHardwareVpdIndex }
                    ::= { bladeHardwareVpdTable 1 }

      BladeHardwareVpdEntry ::= SEQUENCE {
                  bladeHardwareVpdIndex INTEGER,
                  bladeHardwareVpdBayNumber OCTET STRING,
                  bladeHardwareVpdManufacturingId OCTET STRING,
                  bladeHardwareVpdFruNumber OCTET STRING,
                  bladeHardwareVpdHardwareRevision INTEGER,
                  bladeHardwareVpdSerialNumber OCTET STRING,
                  bladeHardwareVpdMachineType OCTET STRING,
                  bladeHardwareVpdUuid OCTET STRING,
                  bladeHardwareVpdManufDate OCTET STRING,
                  bladeHardwareVpdPartNumber OCTET STRING,
                  bladeHardwareVpdFruSerial OCTET STRING,
                  bladeHardwareVpdMachineModel OCTET STRING,
                  bladeHardwareVpdManufacturingIDNumber OCTET STRING,
                  bladeHardwareVpdProductId OCTET STRING,
                  bladeHardwareVpdSubManufacturerId OCTET STRING,
                  bladeHardwareVpdClei OCTET STRING,
                  bladeHardwareVpdHardwareRevisionString OCTET STRING,
                  bladeDaughterVpdCardType INTEGER,
                  bladeDaughterVpdManufacturingId OCTET STRING,
                  bladeDaughterVpdFruNumber OCTET STRING,
                  bladeDaughterVpdHardwareRevision INTEGER,
                  bladeDaughterVpdSerialNumber OCTET STRING,
                  bladeDaughterVpdMachineType OCTET STRING,
                  bladeDaughterVpdUuid OCTET STRING,
                  bladeDaughterVpdManufDate OCTET STRING,
                  bladeDaughterVpdPartNumber OCTET STRING,
                  bladeDaughterVpdFruSerial OCTET STRING,
                  bladeDaughterVpdManufacturingIDNumber OCTET STRING,
                  bladeDaughterVpdProductId OCTET STRING,
                  bladeDaughterVpdSubManufacturerId OCTET STRING,
                  bladeDaughterVpdClei OCTET STRING,
                  bladeDaughterVpdHardwareRevisionString OCTET STRING
                  }

      bladeHardwareVpdIndex  OBJECT-TYPE
                  SYNTAX  Integer32 (0..2147483647) -- was INTEGER
                  MAX-ACCESS  read-only
                  STATUS  current -- was mandatory
                  DESCRIPTION
                  "Blade hardware VPD index.
                  For consistent results, view as a table and not as individual entries."
                  ::= { bladeHardwareVpdEntry 1 }

      bladeHardwareVpdBayNumber  OBJECT-TYPE
                  SYNTAX  OCTET STRING
                  MAX-ACCESS  read-only
                  STATUS  current -- was mandatory
                  DESCRIPTION
                  "Blade hardware VPD Bay number.
                  For consistent results, view as a table and not as individual entries."
                  ::= { bladeHardwareVpdEntry 2 }

      bladeHardwareVpdManufacturingId  OBJECT-TYPE
                  SYNTAX  OCTET STRING
                  MAX-ACCESS  read-only
                  STATUS  current -- was mandatory
                  DESCRIPTION
                  "Blade hardware VPD manufacturing ID.
                  For consistent results, view as a table and not as individual entries."
                  ::= { bladeHardwareVpdEntry 3 }

      bladeHardwareVpdFruNumber  OBJECT-TYPE
                  SYNTAX  OCTET STRING
                  MAX-ACCESS  read-only
                  STATUS  current -- was mandatory
                  DESCRIPTION
                  "Blade hardware VPD FRU number.
                  For consistent results, view as a table and not as individual entries."
                  ::= { bladeHardwareVpdEntry 4 }


      bladeHardwareVpdHardwareRevision  OBJECT-TYPE
                  SYNTAX  INTEGER
                  MAX-ACCESS  read-only
                  STATUS  current -- was mandatory
                  DESCRIPTION
                  "Blade hardware VPD hardware revision.
                  For consistent results, view as a table and not as individual entries.
                  If a hardware revision is programmed in the OEM VPD area for this component,
                  then the HardwareRevisionString version of this MIB object should be used."
                  ::= { bladeHardwareVpdEntry 5 }

      bladeHardwareVpdSerialNumber  OBJECT-TYPE
                  SYNTAX  OCTET STRING
                  MAX-ACCESS  read-only
                  STATUS  current -- was mandatory
                  DESCRIPTION
                  "Blade hardware VPD serial number.
                  For consistent results, view as a table and not as individual entries."
                  ::= { bladeHardwareVpdEntry 6 }

      bladeHardwareVpdMachineType  OBJECT-TYPE
                  SYNTAX  OCTET STRING
                  MAX-ACCESS  read-only
                  STATUS  current -- was mandatory
                  DESCRIPTION
                  "Blade hardware VPD machine type.
                  For consistent results, view as a table and not as individual entries."
                  ::= { bladeHardwareVpdEntry 7 }

      bladeHardwareVpdUuid  OBJECT-TYPE
                  SYNTAX  OCTET STRING
                  MAX-ACCESS  read-only
                  STATUS  current -- was mandatory
                  DESCRIPTION
                  "Blade hardware VPD UUID.
                  For consistent results, view as a table and not as individual entries."
                  ::= { bladeHardwareVpdEntry 8 }

      bladeHardwareVpdManufDate  OBJECT-TYPE
                  SYNTAX  OCTET STRING
                  MAX-ACCESS  read-only
                  STATUS  current -- was mandatory
                  DESCRIPTION
                  "Blade hardware VPD Manufacture Date.
                  For consistent results, view as a table and not as individual entries."
                  ::= { bladeHardwareVpdEntry 9 }

      bladeHardwareVpdPartNumber  OBJECT-TYPE
                  SYNTAX  OCTET STRING
                  MAX-ACCESS  read-only
                  STATUS  current -- was mandatory
                  DESCRIPTION
                  "Blade hardware VPD Part number.
                  For consistent results, view as a table and not as individual entries."
                  ::= { bladeHardwareVpdEntry 10 }

      bladeHardwareVpdFruSerial  OBJECT-TYPE
                  SYNTAX  OCTET STRING
                  MAX-ACCESS  read-only
                  STATUS  current -- was mandatory
                  DESCRIPTION
                  "Blade hardware VPD FRU serial number.
                  For consistent results, view as a table and not as individual entries."
                  ::= { bladeHardwareVpdEntry 11 }

      bladeHardwareVpdMachineModel  OBJECT-TYPE
                  SYNTAX  OCTET STRING
                  MAX-ACCESS  read-only
                  STATUS  current -- was mandatory
                  DESCRIPTION
                  "Blade hardware VPD machine model.
                  For consistent results, view as a table and not as individual entries."
                  ::= { bladeHardwareVpdEntry 12 }

      bladeHardwareVpdManufacturingIDNumber  OBJECT-TYPE
                  SYNTAX  OCTET STRING
                  MAX-ACCESS  read-only
                  STATUS  current -- was mandatory
                  DESCRIPTION
                  "Blade hardware VPD Manufacturer ID Number.
                  For consistent results, view as a table and not as individual entries."
                  ::= { bladeHardwareVpdEntry 13 }

      bladeHardwareVpdProductId  OBJECT-TYPE
                  SYNTAX  OCTET STRING
                  MAX-ACCESS  read-only
                  STATUS  current -- was mandatory
                  DESCRIPTION
                  "Blade hardware VPD product ID.
                  For consistent results, view as a table and not as individual entries."
                  ::= { bladeHardwareVpdEntry 14 }

      bladeHardwareVpdSubManufacturerId  OBJECT-TYPE
                  SYNTAX  OCTET STRING
                  MAX-ACCESS  read-only
                  STATUS  current -- was mandatory
                  DESCRIPTION
                  "Blade hardware VPD subsystem manufacturer ID.
                  For consistent results, view as a table and not as individual entries."
                  ::= { bladeHardwareVpdEntry 15 }

      bladeHardwareVpdClei  OBJECT-TYPE
                  SYNTAX  OCTET STRING
                  MAX-ACCESS  read-only
                  STATUS  current -- was mandatory
                  DESCRIPTION
                  "Blade hardware VPD Common Language Equipment Identifier (CLEI).
                  For consistent results, view as a table and not as individual entries."
                  ::= { bladeHardwareVpdEntry 16 }
       
      bladeHardwareVpdHardwareRevisionString  OBJECT-TYPE
                  SYNTAX  OCTET STRING
                  MAX-ACCESS  read-only
                  STATUS  current -- was mandatory
                  DESCRIPTION
                  "Blade hardware VPD hardware revision in string format.
                  For consistent results, view as a table and not as individual entries.
                  If a hardware revision is programmed in the OEM VPD area for this component,
                  then this MIB object should be used."
                  ::= { bladeHardwareVpdEntry 17 }
                  
      bladeDaughterVpdCardType  OBJECT-TYPE
                  SYNTAX  INTEGER  {
                    unknown(0),
                    networkExpansion(1),
                    storageExpansion(2),
                    pciExpansion(3),
                    genericExpansion(4)
                  }
                  MAX-ACCESS  read-only
                  STATUS  current -- was mandatory
                  DESCRIPTION
                  "Blade expansion card (daughter card) VPD type.  
                  For consistent results, view as a table and not as individual entries."
                  ::= { bladeHardwareVpdEntry 20 }

      bladeDaughterVpdManufacturingId  OBJECT-TYPE
                  SYNTAX  OCTET STRING
                  MAX-ACCESS  read-only
                  STATUS  current -- was mandatory
                  DESCRIPTION
                  "Blade expansion card (daughter card) VPD manufacturing ID.
                  For consistent results, view as a table and not as individual entries."
                  ::= { bladeHardwareVpdEntry 21 }

      bladeDaughterVpdFruNumber  OBJECT-TYPE
                  SYNTAX  OCTET STRING
                  MAX-ACCESS  read-only
                  STATUS  current -- was mandatory
                  DESCRIPTION
                  "Blade expansion card (daughter card) VPD FRU number.
                  For consistent results, view as a table and not as individual entries."
                  ::= { bladeHardwareVpdEntry 22 }


      bladeDaughterVpdHardwareRevision  OBJECT-TYPE
                  SYNTAX  INTEGER
                  MAX-ACCESS  read-only
                  STATUS  current -- was mandatory
                  DESCRIPTION
                  "Blade expansion card (daughter card) VPD hardware revision.
                  For consistent results, view as a table and not as individual entries.
                  If a hardware revision is programmed in the OEM VPD area for this component,
                  then the HardwareRevisionString version of this MIB object should be used."
                  ::= { bladeHardwareVpdEntry 23 }

      bladeDaughterVpdSerialNumber  OBJECT-TYPE
                  SYNTAX  OCTET STRING
                  MAX-ACCESS  read-only
                  STATUS  current -- was mandatory
                  DESCRIPTION
                  "Blade expansion card (daughter card) VPD Serial number.
                  For consistent results, view as a table and not as individual entries."
                  ::= { bladeHardwareVpdEntry 24 }

      bladeDaughterVpdMachineType  OBJECT-TYPE
                  SYNTAX  OCTET STRING
                  MAX-ACCESS  read-only
                  STATUS  current -- was mandatory
                  DESCRIPTION
                  "Blade expansion card (daughter card) VPD Machine type.
                  For consistent results, view as a table and not as individual entries."
                  ::= { bladeHardwareVpdEntry 25 }

      bladeDaughterVpdUuid  OBJECT-TYPE
                  SYNTAX  OCTET STRING
                  MAX-ACCESS  read-only
                  STATUS  current -- was mandatory
                  DESCRIPTION
                  "Blade expansion card (daughter card) VPD UUID.
                  For consistent results, view as a table and not as individual entries."
                  ::= { bladeHardwareVpdEntry 26 }

      bladeDaughterVpdManufDate  OBJECT-TYPE
                  SYNTAX  OCTET STRING
                  MAX-ACCESS  read-only
                  STATUS  current -- was mandatory
                  DESCRIPTION
                  "Blade expansion card (daughter card) VPD Manufacture date.
                  For consistent results, view as a table and not as individual entries."
                  ::= { bladeHardwareVpdEntry 27 }

      bladeDaughterVpdPartNumber  OBJECT-TYPE
                  SYNTAX  OCTET STRING
                  MAX-ACCESS  read-only
                  STATUS  current -- was mandatory
                  DESCRIPTION
                  "Blade expansion card (daughter card) VPD Part number.
                  For consistent results, view as a table and not as individual entries."
                  ::= { bladeHardwareVpdEntry 28 }

      bladeDaughterVpdFruSerial  OBJECT-TYPE
                  SYNTAX  OCTET STRING
                  MAX-ACCESS  read-only
                  STATUS  current -- was mandatory
                  DESCRIPTION
                  "Blade expansion card (daughter card) VPD FRU Serial.
                  For consistent results, view as a table and not as individual entries."
                  ::= { bladeHardwareVpdEntry 29 }

      bladeDaughterVpdManufacturingIDNumber  OBJECT-TYPE
                  SYNTAX  OCTET STRING
                  MAX-ACCESS  read-only
                  STATUS  current -- was mandatory
                  DESCRIPTION
                  "Blade expansion card (daughter card) VPD manufacturer ID Number.
                  For consistent results, view as a table and not as individual entries."
                  ::= { bladeHardwareVpdEntry 30 }

      bladeDaughterVpdProductId  OBJECT-TYPE
                  SYNTAX  OCTET STRING
                  MAX-ACCESS  read-only
                  STATUS  current -- was mandatory
                  DESCRIPTION
                  "Blade expansion card (daughter card) VPD product ID.
                  For consistent results, view as a table and not as individual entries."
                  ::= { bladeHardwareVpdEntry 31 }

        bladeDaughterVpdSubManufacturerId  OBJECT-TYPE
                  SYNTAX  OCTET STRING
                  MAX-ACCESS  read-only
                  STATUS  current -- was mandatory
                  DESCRIPTION
                  "Blade expansion card (daughter card) VPD subsystem manufacturing ID.
                  For consistent results, view as a table and not as individual entries."
                  ::= { bladeHardwareVpdEntry 32 }

      bladeDaughterVpdClei  OBJECT-TYPE
                  SYNTAX  OCTET STRING
                  MAX-ACCESS  read-only
                  STATUS  current -- was mandatory
                  DESCRIPTION
                  "Blade expansion card (daughter card) VPD
                  Common Language Equipment Identifier (CLEI).
                  For consistent results, view as a table and not as individual entries."
                  ::= { bladeHardwareVpdEntry 33 }

      bladeDaughterVpdHardwareRevisionString  OBJECT-TYPE
                  SYNTAX  OCTET STRING
                  MAX-ACCESS  read-only
                  STATUS  current -- was mandatory
                  DESCRIPTION
                  "Blade expansion card (daughter card) VPD hardware revision in string format.
                  For consistent results, view as a table and not as individual entries.
                  If a hardware revision is programmed in the OEM VPD area for this component,
                  then this MIB object should be used."
                  ::= { bladeHardwareVpdEntry 34 }

      -- ********************************************************************************
      -- Blade MAC Address VPD
      -- ********************************************************************************

      bladeMACAddressVpdTable OBJECT-TYPE
                    SYNTAX  SEQUENCE OF BladeMACAddressVpdEntry
                    MAX-ACCESS  not-accessible
                    STATUS  current -- was mandatory
                    DESCRIPTION
                    "Table of MAC addresses of the blade and its expansion cards (daughter cards).
                    For consistent results, view as a table and not as individual entries."
                    ::= { bladeHardwareVpd 2 }

      bladeMACAddressVpdEntry OBJECT-TYPE
                    SYNTAX BladeMACAddressVpdEntry
                    MAX-ACCESS  not-accessible
                    STATUS  current -- was mandatory
                    DESCRIPTION
                    "Blade MAC address entry.  
                    For consistent results, view as a table and not as individual entries."
                    INDEX { bladeMACAddressVpdIndex }
                    ::= { bladeMACAddressVpdTable 1 }


      BladeMACAddressVpdEntry ::= SEQUENCE {
                  bladeMACAddressVpdIndex INTEGER,
                  bladeMACAddress1Vpd              OCTET STRING,
                  bladeMACAddress2Vpd              OCTET STRING,
                  bladeMACAddress3Vpd              OCTET STRING,
                  bladeMACAddress4Vpd              OCTET STRING,
                  bladeMACAddress5Vpd              OCTET STRING,
                  bladeMACAddress6Vpd              OCTET STRING,
                  bladeMACAddress7Vpd              OCTET STRING,
                  bladeMACAddress8Vpd              OCTET STRING,
                  bladeDaughterCard1MACAddress1Vpd OCTET STRING,
                  bladeDaughterCard1MACAddress2Vpd OCTET STRING,
                  bladeDaughterCard1MACAddress3Vpd OCTET STRING,
                  bladeDaughterCard1MACAddress4Vpd OCTET STRING,
                  bladeDaughterCard1MACAddress5Vpd OCTET STRING,
                  bladeDaughterCard1MACAddress6Vpd OCTET STRING,
                  bladeDaughterCard1MACAddress7Vpd OCTET STRING,
                  bladeDaughterCard1MACAddress8Vpd OCTET STRING,
                  bladeDaughterCard2MACAddress1Vpd OCTET STRING,
                  bladeDaughterCard2MACAddress2Vpd OCTET STRING,
                  bladeDaughterCard2MACAddress3Vpd OCTET STRING,
                  bladeDaughterCard2MACAddress4Vpd OCTET STRING,
                  bladeDaughterCard2MACAddress5Vpd OCTET STRING,
                  bladeDaughterCard2MACAddress6Vpd OCTET STRING,
                  bladeDaughterCard2MACAddress7Vpd OCTET STRING,
                  bladeDaughterCard2MACAddress8Vpd OCTET STRING,
                  bladeDaughterCard3MACAddress1Vpd OCTET STRING,
                  bladeDaughterCard3MACAddress2Vpd OCTET STRING,
                  bladeDaughterCard3MACAddress3Vpd OCTET STRING,
                  bladeDaughterCard3MACAddress4Vpd OCTET STRING,
                  bladeDaughterCard3MACAddress5Vpd OCTET STRING,
                  bladeDaughterCard3MACAddress6Vpd OCTET STRING,
                  bladeDaughterCard3MACAddress7Vpd OCTET STRING,
                  bladeDaughterCard3MACAddress8Vpd OCTET STRING,
                  bladeDaughterCard4MACAddress1Vpd OCTET STRING,
                  bladeDaughterCard4MACAddress2Vpd OCTET STRING,
                  bladeDaughterCard4MACAddress3Vpd OCTET STRING,
                  bladeDaughterCard4MACAddress4Vpd OCTET STRING,
                  bladeDaughterCard4MACAddress5Vpd OCTET STRING,
                  bladeDaughterCard4MACAddress6Vpd OCTET STRING,
                  bladeDaughterCard4MACAddress7Vpd OCTET STRING,
                  bladeDaughterCard4MACAddress8Vpd OCTET STRING,
                  bladeDaughterCard5MACAddress1Vpd OCTET STRING,
                  bladeDaughterCard5MACAddress2Vpd OCTET STRING,
                  bladeDaughterCard5MACAddress3Vpd OCTET STRING,
                  bladeDaughterCard5MACAddress4Vpd OCTET STRING,
                  bladeDaughterCard5MACAddress5Vpd OCTET STRING,
                  bladeDaughterCard5MACAddress6Vpd OCTET STRING,
                  bladeDaughterCard5MACAddress7Vpd OCTET STRING,
                  bladeDaughterCard5MACAddress8Vpd OCTET STRING,
                  bladeHSDaughterCard1MACAddress1Vpd OCTET STRING,
                  bladeHSDaughterCard1MACAddress2Vpd OCTET STRING,
                  bladeHSDaughterCard1MACAddress3Vpd OCTET STRING,
                  bladeHSDaughterCard1MACAddress4Vpd OCTET STRING,
                  bladeHSDaughterCard1MACAddress5Vpd OCTET STRING,
                  bladeHSDaughterCard1MACAddress6Vpd OCTET STRING,
                  bladeHSDaughterCard1MACAddress7Vpd OCTET STRING,
                  bladeHSDaughterCard1MACAddress8Vpd OCTET STRING,
                  bladeSideCardMACAddress1Vpd      OCTET STRING,
                  bladeSideCardMACAddress2Vpd      OCTET STRING,
                  bladeSideCardMACAddress3Vpd      OCTET STRING,
                  bladeSideCardMACAddress4Vpd      OCTET STRING,
                  bladeSideCardMACAddress5Vpd      OCTET STRING,
                  bladeSideCardMACAddress6Vpd      OCTET STRING,
                  bladeSideCardMACAddress7Vpd      OCTET STRING,
                  bladeSideCardMACAddress8Vpd      OCTET STRING
                  }

      bladeMACAddressVpdIndex  OBJECT-TYPE
                  SYNTAX  Integer32 (0..2147483647) -- was INTEGER
                  MAX-ACCESS  read-only
                  STATUS  current -- was mandatory
                  DESCRIPTION
                  "Blade index. 
                   For consistent results, view as a table and not as individual entries."
                  ::= { bladeMACAddressVpdEntry 1 }

      bladeMACAddress1Vpd  OBJECT-TYPE
                  SYNTAX  OCTET STRING
                  MAX-ACCESS  read-only
                  STATUS  current -- was mandatory
                  DESCRIPTION
                  "Blade MAC address 1.  
                  For consistent results, view as a table and not as individual entries."
                  ::= { bladeMACAddressVpdEntry 2 }

      bladeMACAddress2Vpd  OBJECT-TYPE
                  SYNTAX  OCTET STRING
                  MAX-ACCESS  read-only
                  STATUS  current -- was mandatory
                  DESCRIPTION
                  "Blade MAC address 2.  
                  For consistent results, view as a table and not as individual entries."
                  ::= { bladeMACAddressVpdEntry 3 }

      bladeMACAddress3Vpd  OBJECT-TYPE
                  SYNTAX  OCTET STRING
                  MAX-ACCESS  read-only
                  STATUS  current -- was mandatory
                  DESCRIPTION
                  "Blade MAC address 3.  
                  For consistent results, view as a table and not as individual entries."
                  ::= { bladeMACAddressVpdEntry 4 }

      bladeMACAddress4Vpd  OBJECT-TYPE
                  SYNTAX  OCTET STRING
                  MAX-ACCESS  read-only
                  STATUS  current -- was mandatory
                  DESCRIPTION
                  "Blade MAC address 4.  
                  For consistent results, view as a table and not as individual entries."
                  ::= { bladeMACAddressVpdEntry 5 }

      bladeMACAddress5Vpd  OBJECT-TYPE
                  SYNTAX  OCTET STRING
                  MAX-ACCESS  read-only
                  STATUS  current -- was mandatory
                  DESCRIPTION
                  "Blade MAC address 5.  
                  For consistent results, view as a table and not as individual entries."
                  ::= { bladeMACAddressVpdEntry 6 }

      bladeMACAddress6Vpd  OBJECT-TYPE
                  SYNTAX  OCTET STRING
                  MAX-ACCESS  read-only
                  STATUS  current -- was mandatory
                  DESCRIPTION
                  "Blade MAC address 6.  
                  For consistent results, view as a table and not as individual entries."
                  ::= { bladeMACAddressVpdEntry 7 }

      bladeMACAddress7Vpd  OBJECT-TYPE
                  SYNTAX  OCTET STRING
                  MAX-ACCESS  read-only
                  STATUS  current -- was mandatory
                  DESCRIPTION
                  "Blade MAC address 7.  
                  For consistent results, view as a table and not as individual entries."
                  ::= { bladeMACAddressVpdEntry 8 }

      bladeMACAddress8Vpd  OBJECT-TYPE
                  SYNTAX  OCTET STRING
                  MAX-ACCESS  read-only
                  STATUS  current -- was mandatory
                  DESCRIPTION
                  "Blade MAC address 8.  
                  For consistent results, view as a table and not as individual entries."
                  ::= { bladeMACAddressVpdEntry 9 }

      bladeDaughterCard1MACAddress1Vpd  OBJECT-TYPE
                  SYNTAX  OCTET STRING
                  MAX-ACCESS  read-only
                  STATUS  current -- was mandatory
                  DESCRIPTION
                  "Blade expansion card (daughter card) 1 MAC address 1.  
                  For consistent results, view as a table and not as individual entries."
                  ::= { bladeMACAddressVpdEntry 10 }

      bladeDaughterCard1MACAddress2Vpd  OBJECT-TYPE
                  SYNTAX  OCTET STRING
                  MAX-ACCESS  read-only
                  STATUS  current -- was mandatory
                  DESCRIPTION
                  "Blade expansion card (daughter card) 1 MAC address 2.  
                  For consistent results, view as a table and not as individual entries."
                  ::= { bladeMACAddressVpdEntry 11 }

      bladeDaughterCard1MACAddress3Vpd  OBJECT-TYPE
                  SYNTAX  OCTET STRING
                  MAX-ACCESS  read-only
                  STATUS  current -- was mandatory
                  DESCRIPTION
                  "Blade expansion card (daughter card) 1 MAC address 3.  
                  For consistent results, view as a table and not as individual entries."
                  ::= { bladeMACAddressVpdEntry 12 }

      bladeDaughterCard1MACAddress4Vpd  OBJECT-TYPE
                  SYNTAX  OCTET STRING
                  MAX-ACCESS  read-only
                  STATUS  current -- was mandatory
                  DESCRIPTION
                  "Blade expansion card (daughter card) 1 MAC address 4.  
                  For consistent results, view as a table and not as individual entries."
                  ::= { bladeMACAddressVpdEntry 13 }

      bladeDaughterCard1MACAddress5Vpd  OBJECT-TYPE
                  SYNTAX  OCTET STRING
                  MAX-ACCESS  read-only
                  STATUS  current -- was mandatory
                  DESCRIPTION
                  "Blade expansion card (daughter card) 1 MAC address 5.  
                  For consistent results, view as a table and not as individual entries."
                  ::= { bladeMACAddressVpdEntry 14 }

      bladeDaughterCard1MACAddress6Vpd  OBJECT-TYPE
                  SYNTAX  OCTET STRING
                  MAX-ACCESS  read-only
                  STATUS  current -- was mandatory
                  DESCRIPTION
                  "Blade expansion card (daughter card) 1 MAC address 6.  
                  For consistent results, view as a table and not as individual entries."
                  ::= { bladeMACAddressVpdEntry 15 }

      bladeDaughterCard1MACAddress7Vpd  OBJECT-TYPE
                  SYNTAX  OCTET STRING
                  MAX-ACCESS  read-only
                  STATUS  current -- was mandatory
                  DESCRIPTION
                  "Blade expansion card (daughter card) 1 MAC address 7.  
                  For consistent results, view as a table and not as individual entries."
                  ::= { bladeMACAddressVpdEntry 16 }

      bladeDaughterCard1MACAddress8Vpd  OBJECT-TYPE
                  SYNTAX  OCTET STRING
                  MAX-ACCESS  read-only
                  STATUS  current -- was mandatory
                  DESCRIPTION
                  "Blade expansion card (daughter card) 1 MAC address 8.  
                  For consistent results, view as a table and not as individual entries."
                  ::= { bladeMACAddressVpdEntry 17 }

      bladeDaughterCard2MACAddress1Vpd  OBJECT-TYPE
                  SYNTAX  OCTET STRING
                  MAX-ACCESS  read-only
                  STATUS  current -- was mandatory
                  DESCRIPTION
                  "Blade expansion card (daughter card) 2 MAC address 1.  
                  For consistent results, view as a table and not as individual entries."
                  ::= { bladeMACAddressVpdEntry 18 }

      bladeDaughterCard2MACAddress2Vpd  OBJECT-TYPE
                  SYNTAX  OCTET STRING
                  MAX-ACCESS  read-only
                  STATUS  current -- was mandatory
                  DESCRIPTION
                  "Blade expansion card (daughter card) 2 MAC address 2.  
                  For consistent results, view as a table and not as individual entries."
                  ::= { bladeMACAddressVpdEntry 19 }

      bladeDaughterCard2MACAddress3Vpd  OBJECT-TYPE
                  SYNTAX  OCTET STRING
                  MAX-ACCESS  read-only
                  STATUS  current -- was mandatory
                  DESCRIPTION
                  "Blade expansion card (daughter card) 2 MAC address 3.  
                  For consistent results, view as a table and not as individual entries."
                  ::= { bladeMACAddressVpdEntry 20 }

      bladeDaughterCard2MACAddress4Vpd  OBJECT-TYPE
                  SYNTAX  OCTET STRING
                  MAX-ACCESS  read-only
                  STATUS  current -- was mandatory
                  DESCRIPTION
                  "Blade expansion card (daughter card) 2 MAC address 4.  
                  For consistent results, view as a table and not as individual entries."
                  ::= { bladeMACAddressVpdEntry 21 }

      bladeDaughterCard2MACAddress5Vpd  OBJECT-TYPE
                  SYNTAX  OCTET STRING
                  MAX-ACCESS  read-only
                  STATUS  current -- was mandatory
                  DESCRIPTION
                  "Blade expansion card (daughter card) 2 MAC address 5.  
                  For consistent results, view as a table and not as individual entries."
                  ::= { bladeMACAddressVpdEntry 22 }

      bladeDaughterCard2MACAddress6Vpd  OBJECT-TYPE
                  SYNTAX  OCTET STRING
                  MAX-ACCESS  read-only
                  STATUS  current -- was mandatory
                  DESCRIPTION
                  "Blade expansion card (daughter card) 2 MAC address 6.  
                  For consistent results, view as a table and not as individual entries."
                  ::= { bladeMACAddressVpdEntry 23 }

      bladeDaughterCard2MACAddress7Vpd  OBJECT-TYPE
                  SYNTAX  OCTET STRING
                  MAX-ACCESS  read-only
                  STATUS  current -- was mandatory
                  DESCRIPTION
                  "Blade expansion card (daughter card) 2 MAC address 7.  
                  For consistent results, view as a table and not as individual entries."
                  ::= { bladeMACAddressVpdEntry 24 }

      bladeDaughterCard2MACAddress8Vpd  OBJECT-TYPE
                  SYNTAX  OCTET STRING
                  MAX-ACCESS  read-only
                  STATUS  current -- was mandatory
                  DESCRIPTION
                  "Blade expansion card (daughter card) 2 MAC address 8.  
                  For consistent results, view as a table and not as individual entries."
                  ::= { bladeMACAddressVpdEntry 25 }

      bladeDaughterCard3MACAddress1Vpd  OBJECT-TYPE
                  SYNTAX  OCTET STRING
                  MAX-ACCESS  read-only
                  STATUS  current -- was mandatory
                  DESCRIPTION
                  "Blade expansion card (daughter card) 3 MAC address 1.  
                  For consistent results, view as a table and not as individual entries."
                  ::= { bladeMACAddressVpdEntry 26 }

      bladeDaughterCard3MACAddress2Vpd  OBJECT-TYPE
                  SYNTAX  OCTET STRING
                  MAX-ACCESS  read-only
                  STATUS  current -- was mandatory
                  DESCRIPTION
                  "Blade expansion card (daughter card) 3 MAC address 2.  
                  For consistent results, view as a table and not as individual entries."
                  ::= { bladeMACAddressVpdEntry 27 }

      bladeDaughterCard3MACAddress3Vpd  OBJECT-TYPE
                  SYNTAX  OCTET STRING
                  MAX-ACCESS  read-only
                  STATUS  current -- was mandatory
                  DESCRIPTION
                  "Blade expansion card (daughter card) 3 MAC address 3.  
                  For consistent results, view as a table and not as individual entries."
                  ::= { bladeMACAddressVpdEntry 28 }

      bladeDaughterCard3MACAddress4Vpd  OBJECT-TYPE
                  SYNTAX  OCTET STRING
                  MAX-ACCESS  read-only
                  STATUS  current -- was mandatory
                  DESCRIPTION
                  "Blade expansion card (daughter card) 3 MAC address 4.  
                  For consistent results, view as a table and not as individual entries."
                  ::= { bladeMACAddressVpdEntry 29 }

      bladeDaughterCard3MACAddress5Vpd  OBJECT-TYPE
                  SYNTAX  OCTET STRING
                  MAX-ACCESS  read-only
                  STATUS  current -- was mandatory
                  DESCRIPTION
                  "Blade expansion card (daughter card) 3 MAC address 5.  
                  For consistent results, view as a table and not as individual entries."
                  ::= { bladeMACAddressVpdEntry 30 }

      bladeDaughterCard3MACAddress6Vpd  OBJECT-TYPE
                  SYNTAX  OCTET STRING
                  MAX-ACCESS  read-only
                  STATUS  current -- was mandatory
                  DESCRIPTION
                  "Blade expansion card (daughter card) 3 MAC address 6.  
                  For consistent results, view as a table and not as individual entries."
                  ::= { bladeMACAddressVpdEntry 31 }

      bladeDaughterCard3MACAddress7Vpd  OBJECT-TYPE
                  SYNTAX  OCTET STRING
                  MAX-ACCESS  read-only
                  STATUS  current -- was mandatory
                  DESCRIPTION
                  "Blade expansion card (daughter card) 3 MAC address 7.  
                  For consistent results, view as a table and not as individual entries."
                  ::= { bladeMACAddressVpdEntry 32 }

      bladeDaughterCard3MACAddress8Vpd  OBJECT-TYPE
                  SYNTAX  OCTET STRING
                  MAX-ACCESS  read-only
                  STATUS  current -- was mandatory
                  DESCRIPTION
                  "Blade expansion card (daughter card) 3 MAC address 8.  
                  For consistent results, view as a table and not as individual entries."
                  ::= { bladeMACAddressVpdEntry 33 }

      bladeDaughterCard4MACAddress1Vpd  OBJECT-TYPE
                  SYNTAX  OCTET STRING
                  MAX-ACCESS  read-only
                  STATUS  current -- was mandatory
                  DESCRIPTION
                  "Blade expansion card (daughter card) 4 MAC address 1.  
                  For consistent results, view as a table and not as individual entries."
                  ::= { bladeMACAddressVpdEntry 34 }

      bladeDaughterCard4MACAddress2Vpd  OBJECT-TYPE
                  SYNTAX  OCTET STRING
                  MAX-ACCESS  read-only
                  STATUS  current -- was mandatory
                  DESCRIPTION
                  "Blade expansion card (daughter card) 4 MAC address 2.  
                  For consistent results, view as a table and not as individual entries."
                  ::= { bladeMACAddressVpdEntry 35 }

      bladeDaughterCard4MACAddress3Vpd  OBJECT-TYPE
                  SYNTAX  OCTET STRING
                  MAX-ACCESS  read-only
                  STATUS  current -- was mandatory
                  DESCRIPTION
                  "Blade expansion card (daughter card) 4 MAC address 3.  
                  For consistent results, view as a table and not as individual entries."
                  ::= { bladeMACAddressVpdEntry 36 }

      bladeDaughterCard4MACAddress4Vpd  OBJECT-TYPE
                  SYNTAX  OCTET STRING
                  MAX-ACCESS  read-only
                  STATUS  current -- was mandatory
                  DESCRIPTION
                  "Blade expansion card (daughter card) 4 MAC address 4.  
                  For consistent results, view as a table and not as individual entries."
                  ::= { bladeMACAddressVpdEntry 37 }
      
      bladeDaughterCard4MACAddress5Vpd  OBJECT-TYPE
                  SYNTAX  OCTET STRING
                  MAX-ACCESS  read-only
                  STATUS  current -- was mandatory
                  DESCRIPTION
                  "Blade expansion card (daughter card) 4 MAC address 5.  
                  For consistent results, view as a table and not as individual entries."
                  ::= { bladeMACAddressVpdEntry 38 }
      
      bladeDaughterCard4MACAddress6Vpd  OBJECT-TYPE
                  SYNTAX  OCTET STRING
                  MAX-ACCESS  read-only
                  STATUS  current -- was mandatory
                  DESCRIPTION
                  "Blade expansion card (daughter card) 4 MAC address 6.  
                  For consistent results, view as a table and not as individual entries."
                  ::= { bladeMACAddressVpdEntry 39 }
      
      bladeDaughterCard4MACAddress7Vpd  OBJECT-TYPE
                  SYNTAX  OCTET STRING
                  MAX-ACCESS  read-only
                  STATUS  current -- was mandatory
                  DESCRIPTION
                  "Blade expansion card (daughter card) 4 MAC address 7.  
                  For consistent results, view as a table and not as individual entries."
                  ::= { bladeMACAddressVpdEntry 40 }
      
      bladeDaughterCard4MACAddress8Vpd  OBJECT-TYPE
                  SYNTAX  OCTET STRING
                  MAX-ACCESS  read-only
                  STATUS  current -- was mandatory
                  DESCRIPTION
                  "Blade expansion card (daughter card) 4 MAC address 8.  
                  For consistent results, view as a table and not as individual entries."
                  ::= { bladeMACAddressVpdEntry 41 }
      
      bladeDaughterCard5MACAddress1Vpd  OBJECT-TYPE
                  SYNTAX  OCTET STRING
                  MAX-ACCESS  read-only
                  STATUS  current -- was mandatory
                  DESCRIPTION
                  "Blade expansion card (daughter card) 5 MAC address 1.  
                  For consistent results, view as a table and not as individual entries."
                  ::= { bladeMACAddressVpdEntry 42 }

      bladeDaughterCard5MACAddress2Vpd  OBJECT-TYPE
                  SYNTAX  OCTET STRING
                  MAX-ACCESS  read-only
                  STATUS  current -- was mandatory
                  DESCRIPTION
                  "Blade expansion card (daughter card) 5 MAC address 2.  
                  For consistent results, view as a table and not as individual entries."
                  ::= { bladeMACAddressVpdEntry 43 }

      bladeDaughterCard5MACAddress3Vpd  OBJECT-TYPE
                  SYNTAX  OCTET STRING
                  MAX-ACCESS  read-only
                  STATUS  current -- was mandatory
                  DESCRIPTION
                  "Blade expansion card (daughter card) 5 MAC address 3.  
                  For consistent results, view as a table and not as individual entries."
                  ::= { bladeMACAddressVpdEntry 44}

      bladeDaughterCard5MACAddress4Vpd  OBJECT-TYPE
                  SYNTAX  OCTET STRING
                  MAX-ACCESS  read-only
                  STATUS  current -- was mandatory
                  DESCRIPTION
                  "Blade expansion card (daughter card) 5 MAC address 4.  
                  For consistent results, view as a table and not as individual entries."
                  ::= { bladeMACAddressVpdEntry 45 }

      bladeDaughterCard5MACAddress5Vpd  OBJECT-TYPE
                  SYNTAX  OCTET STRING
                  MAX-ACCESS  read-only
                  STATUS  current -- was mandatory
                  DESCRIPTION
                  "Blade expansion card (daughter card) 5 MAC address 5.  
                  For consistent results, view as a table and not as individual entries."
                  ::= { bladeMACAddressVpdEntry 46 }

      bladeDaughterCard5MACAddress6Vpd  OBJECT-TYPE
                  SYNTAX  OCTET STRING
                  MAX-ACCESS  read-only
                  STATUS  current -- was mandatory
                  DESCRIPTION
                  "Blade expansion card (daughter card) 5 MAC address 6.  
                  For consistent results, view as a table and not as individual entries."
                  ::= { bladeMACAddressVpdEntry 47 }

      bladeDaughterCard5MACAddress7Vpd  OBJECT-TYPE
                  SYNTAX  OCTET STRING
                  MAX-ACCESS  read-only
                  STATUS  current -- was mandatory
                  DESCRIPTION
                  "Blade expansion card (daughter card) 5 MAC address 7.  
                  For consistent results, view as a table and not as individual entries."
                  ::= { bladeMACAddressVpdEntry 48 }

      bladeDaughterCard5MACAddress8Vpd  OBJECT-TYPE
                  SYNTAX  OCTET STRING
                  MAX-ACCESS  read-only
                  STATUS  current -- was mandatory
                  DESCRIPTION
                  "Blade expansion card (daughter card) 5 MAC address 8.  
                  For consistent results, view as a table and not as individual entries."
                  ::= { bladeMACAddressVpdEntry 49 }

      bladeHSDaughterCard1MACAddress1Vpd  OBJECT-TYPE
                  SYNTAX  OCTET STRING
                  MAX-ACCESS  read-only
                  STATUS  current -- was mandatory
                  DESCRIPTION
                  "Blade high speed expansion card (daughter card) 1 MAC address 1.  
                  For consistent results, view  as a table and not as individual entries."
                  ::= { bladeMACAddressVpdEntry 100 }

      bladeHSDaughterCard1MACAddress2Vpd  OBJECT-TYPE
                  SYNTAX  OCTET STRING
                  MAX-ACCESS  read-only
                  STATUS  current -- was mandatory
                  DESCRIPTION
                  "Blade high speed expansion card (daughter card) 1 MAC address 2.  
                  For consistent results, view as a table and not as individual entries."
                  ::= { bladeMACAddressVpdEntry 101 }

      bladeHSDaughterCard1MACAddress3Vpd  OBJECT-TYPE
                  SYNTAX  OCTET STRING
                  MAX-ACCESS  read-only
                  STATUS  current -- was mandatory
                  DESCRIPTION
                  "Blade high speed expansion card (daughter card) 1 MAC address 3.  
                  For consistent results, view as a table and not as individual entries."
                  ::= { bladeMACAddressVpdEntry 102}

      bladeHSDaughterCard1MACAddress4Vpd  OBJECT-TYPE
                  SYNTAX  OCTET STRING
                  MAX-ACCESS  read-only
                  STATUS  current -- was mandatory
                  DESCRIPTION
                  "Blade high speed expansion card (daughter card) 1 MAC address 4.  
                  For consistent results, view as a table and not as individual entries."
                  ::= { bladeMACAddressVpdEntry 103 }

      bladeHSDaughterCard1MACAddress5Vpd  OBJECT-TYPE
                  SYNTAX  OCTET STRING
                  MAX-ACCESS  read-only
                  STATUS  current -- was mandatory
                  DESCRIPTION
                  "Blade high speed expansion card (daughter card) 1 MAC address 5.  
                  For consistent results, view as a table and not as individual entries."
                  ::= { bladeMACAddressVpdEntry 104 }
      
      bladeHSDaughterCard1MACAddress6Vpd  OBJECT-TYPE
                  SYNTAX  OCTET STRING
                  MAX-ACCESS  read-only
                  STATUS  current -- was mandatory
                  DESCRIPTION
                  "Blade high speed expansion card (daughter card) 1 MAC address 6.  
                  For consistent results, view as a table and not as individual entries."
                  ::= { bladeMACAddressVpdEntry 105 }
      
      bladeHSDaughterCard1MACAddress7Vpd  OBJECT-TYPE
                  SYNTAX  OCTET STRING
                  MAX-ACCESS  read-only
                  STATUS  current -- was mandatory
                  DESCRIPTION
                  "Blade high speed expansion card (daughter card) 1 MAC address 7.  
                  For consistent results, view as a table and not as individual entries."
                  ::= { bladeMACAddressVpdEntry 106 }
      
      bladeHSDaughterCard1MACAddress8Vpd  OBJECT-TYPE
                  SYNTAX  OCTET STRING
                  MAX-ACCESS  read-only
                  STATUS  current -- was mandatory
                  DESCRIPTION
                  "Blade high speed expansion card (daughter card) 1 MAC address 8.  
                  For consistent results, view as a table and not as individual entries."
                  ::= { bladeMACAddressVpdEntry 107 }
      
      bladeSideCardMACAddress1Vpd  OBJECT-TYPE
                  SYNTAX  OCTET STRING
                  MAX-ACCESS  read-only
                  STATUS  current -- was mandatory
                  DESCRIPTION
                  "Blade side card MAC address 1.  
                  For consistent results, view as a table and not as individual entries."
                  ::= { bladeMACAddressVpdEntry 164 }
                  
      bladeSideCardMACAddress2Vpd  OBJECT-TYPE
                  SYNTAX  OCTET STRING
                  MAX-ACCESS  read-only
                  STATUS  current -- was mandatory
                  DESCRIPTION
                  "Blade side card MAC address 2.  
                  For consistent results, view as a table and not as individual entries."
                  ::= { bladeMACAddressVpdEntry 165 }
                  
      bladeSideCardMACAddress3Vpd  OBJECT-TYPE
                  SYNTAX  OCTET STRING
                  MAX-ACCESS  read-only
                  STATUS  current -- was mandatory
                  DESCRIPTION
                  "Blade side card MAC address 3.  
                  For consistent results, view as a table and not as individual entries."
                  ::= { bladeMACAddressVpdEntry 166 }
                  
      bladeSideCardMACAddress4Vpd  OBJECT-TYPE
                  SYNTAX  OCTET STRING
                  MAX-ACCESS  read-only
                  STATUS  current -- was mandatory
                  DESCRIPTION
                  "Blade side card MAC address 4.  
                  For consistent results, view as a table and not as individual entries."
                  ::= { bladeMACAddressVpdEntry 167 }
                  
      bladeSideCardMACAddress5Vpd  OBJECT-TYPE
                  SYNTAX  OCTET STRING
                  MAX-ACCESS  read-only
                  STATUS  current -- was mandatory
                  DESCRIPTION
                  "Blade side card MAC address 5.  
                  For consistent results, view as a table and not as individual entries."
                  ::= { bladeMACAddressVpdEntry 168 }
                  
      bladeSideCardMACAddress6Vpd  OBJECT-TYPE
                  SYNTAX  OCTET STRING
                  MAX-ACCESS  read-only
                  STATUS  current -- was mandatory
                  DESCRIPTION
                  "Blade side card MAC address 6.  
                  For consistent results, view as a table and not as individual entries."
                  ::= { bladeMACAddressVpdEntry 169 }
                  
      bladeSideCardMACAddress7Vpd  OBJECT-TYPE
                  SYNTAX  OCTET STRING
                  MAX-ACCESS  read-only
                  STATUS  current -- was mandatory
                  DESCRIPTION
                  "Blade side card MAC address 7.  
                  For consistent results, view as a table and not as individual entries."
                  ::= { bladeMACAddressVpdEntry 170 }
                  
      bladeSideCardMACAddress8Vpd  OBJECT-TYPE
                  SYNTAX  OCTET STRING
                  MAX-ACCESS  read-only
                  STATUS  current -- was mandatory
                  DESCRIPTION
                  "Blade side card MAC address 8.  
                  For consistent results, view as a table and not as individual entries."
                  ::= { bladeMACAddressVpdEntry 171 }

      -- ********************************************************************************
      -- Blade Expansion Board VPD
      -- ********************************************************************************

      bladeExpBoardVpdTable OBJECT-TYPE
                    SYNTAX  SEQUENCE OF BladeExpBoardVpdEntry
                    MAX-ACCESS  not-accessible
                    STATUS  current -- was mandatory
                    DESCRIPTION
                    "Table of VPD information for the blade expansion board components.
                    For consistent results, view as a table and not as individual entries."
                    ::= { bladeHardwareVpd 3 }

      bladeExpBoardVpdEntry OBJECT-TYPE
                    SYNTAX BladeExpBoardVpdEntry
                    MAX-ACCESS  not-accessible
                    STATUS  current -- was mandatory
                    DESCRIPTION
                    "Blade expansion board VPD entry.
                    For consistent results, view as a table and not as individual entries."
                    INDEX { bladeExpBoardVpdIndex }
                    ::= { bladeExpBoardVpdTable 1 }

      BladeExpBoardVpdEntry ::= SEQUENCE {
                  bladeExpBoardVpdIndex INTEGER,
                  bladeExpBoardVpdBayNumber OCTET STRING,
                  bladeExpBoardVpdManufacturingId OCTET STRING,
                  bladeExpBoardVpdFruNumber OCTET STRING,
                  bladeExpBoardVpdHardwareRevision INTEGER,
                  bladeExpBoardVpdSerialNumber OCTET STRING,
                  bladeExpBoardVpdMachineType OCTET STRING,
                  bladeExpBoardVpdUuid OCTET STRING,
                  bladeExpBoardVpdManufDate OCTET STRING,
                  bladeExpBoardVpdPartNumber OCTET STRING,
                  bladeExpBoardVpdFruSerial OCTET STRING,
                  bladeExpBoardVpdMachineModel OCTET STRING,
                  bladeExpBoardVpdManufacturingIDNumber OCTET STRING,
                  bladeExpBoardVpdProductId OCTET STRING,
                  bladeExpBoardVpdSubManufacturerId OCTET STRING,
                  bladeExpBoardVpdClei OCTET STRING,
                  bladeExpBoardVpdBladeBayNumber OCTET STRING,
                  bladeExpBoardVpdCardType INTEGER,
                  bladeExpBoardVpdCardSubType INTEGER,
                  bladeExpBoardVpdHardwareRevisionString OCTET STRING
                  }

      bladeExpBoardVpdIndex  OBJECT-TYPE
                  SYNTAX  Integer32 (0..2147483647) -- was INTEGER
                  MAX-ACCESS  read-only
                  STATUS  current -- was mandatory
                  DESCRIPTION
                  "Blade expansion board VPD index.
                  For consistent results, view as a table and not as individual entries."
                  ::= { bladeExpBoardVpdEntry 1 }

      bladeExpBoardVpdBayNumber  OBJECT-TYPE
                  SYNTAX  OCTET STRING
                  MAX-ACCESS  read-only
                  STATUS  current -- was mandatory
                  DESCRIPTION
                  "Blade expansion board VPD Bay number.
                  For consistent results, view as a table and not as individual entries."
                  ::= { bladeExpBoardVpdEntry 2 }

      bladeExpBoardVpdManufacturingId  OBJECT-TYPE
                  SYNTAX  OCTET STRING
                  MAX-ACCESS  read-only
                  STATUS  current -- was mandatory
                  DESCRIPTION
                  "Blade expansion board VPD manufacturing ID.
                  For consistent results, view as a table and not as individual entries."
                  ::= { bladeExpBoardVpdEntry 3 }

      bladeExpBoardVpdFruNumber  OBJECT-TYPE
                  SYNTAX  OCTET STRING
                  MAX-ACCESS  read-only
                  STATUS  current -- was mandatory
                  DESCRIPTION
                  "Blade expansion board VPD FRU number.
                  For consistent results, view as a table and not as individual entries."
                  ::= { bladeExpBoardVpdEntry 4 }


      bladeExpBoardVpdHardwareRevision  OBJECT-TYPE
                  SYNTAX  INTEGER
                  MAX-ACCESS  read-only
                  STATUS  current -- was mandatory
                  DESCRIPTION
                  "Blade expansion board VPD hardware revision.
                  For consistent results, view as a table and not as individual entries.
                  If a hardware revision is programmed in the OEM VPD area for this component,
                  then the HardwareRevisionString version of this MIB object should be used."
                  ::= { bladeExpBoardVpdEntry 5 }

      bladeExpBoardVpdSerialNumber  OBJECT-TYPE
                  SYNTAX  OCTET STRING
                  MAX-ACCESS  read-only
                  STATUS  current -- was mandatory
                  DESCRIPTION
                  "Blade expansion board VPD serial number.
                  For consistent results, view as a table and not as individual entries."
                  ::= { bladeExpBoardVpdEntry 6 }

      bladeExpBoardVpdMachineType  OBJECT-TYPE
                  SYNTAX  OCTET STRING
                  MAX-ACCESS  read-only
                  STATUS  current -- was mandatory
                  DESCRIPTION
                  "Blade expansion board VPD machine type.
                  For consistent results, view as a table and not as individual entries."
                  ::= { bladeExpBoardVpdEntry 7 }

      bladeExpBoardVpdUuid  OBJECT-TYPE
                  SYNTAX  OCTET STRING
                  MAX-ACCESS  read-only
                  STATUS  current -- was mandatory
                  DESCRIPTION
                  "Blade expansion board VPD UUID.
                  For consistent results, view as a table and not as individual entries."
                  ::= { bladeExpBoardVpdEntry 8 }

      bladeExpBoardVpdManufDate  OBJECT-TYPE
                  SYNTAX  OCTET STRING
                  MAX-ACCESS  read-only
                  STATUS  current -- was mandatory
                  DESCRIPTION
                  "Blade expansion board VPD Manufacture Date.
                  For consistent results, view as a table and not as individual entries."
                  ::= { bladeExpBoardVpdEntry 9 }

      bladeExpBoardVpdPartNumber  OBJECT-TYPE
                  SYNTAX  OCTET STRING
                  MAX-ACCESS  read-only
                  STATUS  current -- was mandatory
                  DESCRIPTION
                  "Blade expansion board VPD Part number.
                  For consistent results, view as a table and not as individual entries."
                  ::= { bladeExpBoardVpdEntry 10 }

      bladeExpBoardVpdFruSerial  OBJECT-TYPE
                  SYNTAX  OCTET STRING
                  MAX-ACCESS  read-only
                  STATUS  current -- was mandatory
                  DESCRIPTION
                  "Blade expansion board VPD FRU serial number.
                  For consistent results, view as a table and not as individual entries."
                  ::= { bladeExpBoardVpdEntry 11 }

       bladeExpBoardVpdMachineModel  OBJECT-TYPE
                  SYNTAX  OCTET STRING
                  MAX-ACCESS  read-only
                  STATUS  current -- was mandatory
                  DESCRIPTION
                  "Blade expansion board VPD machine model.
                  For consistent results, view as a table and not as individual entries."
                  ::= { bladeExpBoardVpdEntry 12 }

      bladeExpBoardVpdManufacturingIDNumber  OBJECT-TYPE
                  SYNTAX  OCTET STRING
                  MAX-ACCESS  read-only
                  STATUS  current -- was mandatory
                  DESCRIPTION
                  "Blade expansion board VPD Manufacturer ID Number.
                  For consistent results, view as a table and not as individual entries."
                  ::= { bladeExpBoardVpdEntry 13 }

       bladeExpBoardVpdProductId  OBJECT-TYPE
                  SYNTAX  OCTET STRING
                  MAX-ACCESS  read-only
                  STATUS  current -- was mandatory
                  DESCRIPTION
                  "Blade expansion board VPD Product ID.
                  For consistent results, view as a table and
                  not as individual entries."
                  ::= { bladeExpBoardVpdEntry 14 }

       bladeExpBoardVpdSubManufacturerId  OBJECT-TYPE
                  SYNTAX  OCTET STRING
                  MAX-ACCESS  read-only
                  STATUS  current -- was mandatory
                  DESCRIPTION
                  "Blade expansion board VPD subsystem manufacturer ID.
                  For consistent results, view as a table and not as individual entries."
                  ::= { bladeExpBoardVpdEntry 15 }

       bladeExpBoardVpdClei  OBJECT-TYPE
                  SYNTAX  OCTET STRING
                  MAX-ACCESS  read-only
                  STATUS  current -- was mandatory
                  DESCRIPTION
                  "Blade expansion board VPD Common Language Equipment Identifier (CLEI).
                  For consistent results, view as a table and not as individual entries."
                  ::= { bladeExpBoardVpdEntry 16 }

       bladeExpBoardVpdBladeBayNumber  OBJECT-TYPE
                  SYNTAX  OCTET STRING
                  MAX-ACCESS  read-only
                  STATUS  current -- was mandatory
                  DESCRIPTION
                  "Blade bay number of the blade expansion board. 
                  For consistent results, view as a table and not as individual entries."
                  ::= { bladeExpBoardVpdEntry 19 }
       
       bladeExpBoardVpdCardType  OBJECT-TYPE
                  SYNTAX  INTEGER  {
                    unknown(0),
                    storageExpansion(1),
                    pciExpansion(2)
                  }
                  MAX-ACCESS  read-only
                  STATUS  current -- was mandatory
                  DESCRIPTION
                  "Blade expansion board VPD type.
                  For consistent results, view as a table and  not as individual entries."
                  ::= { bladeExpBoardVpdEntry 20 }   
                  
       bladeExpBoardVpdCardSubType  OBJECT-TYPE
                  SYNTAX  INTEGER  {
                    unknown(0),
                    bse1(1),
                    bse2(2), 
                    bse3(3),
                    peu1(11),
                    peu2(12),
                    peu3(13),
                    bie(21)
                  }
                  MAX-ACCESS  read-only
                  STATUS  current -- was mandatory
                  DESCRIPTION
                  "Blade expansion board VPD subtype. 
                  Describes the expansion board type with more granularity.
                  bse1,bse2,bse3 = Blade Storage Expansion (1st, 2nd, and 3rd Generations),
                  peu1 = PCI Expansion (1st  Generation), 
                  peu2 = PCI Expansion Unit II,
                  peu3 = bpe3 = PCI Express Expansion Unit,
                  bie= Blade I/O Expansion
                  For consistent results, view as a table and  not as individual entries."
                  ::= { bladeExpBoardVpdEntry 21 }
           
      bladeExpBoardVpdHardwareRevisionString  OBJECT-TYPE
                  SYNTAX  OCTET STRING
                  MAX-ACCESS  read-only
                  STATUS  current -- was mandatory
                  DESCRIPTION
                  "Blade expansion board VPD hardware revision in string format.
                  For consistent results, view as a table and not as individual entries.
                  If a hardware revision is programmed in the OEM VPD area for this component,
                  then this MIB object should be used."
                  ::= { bladeExpBoardVpdEntry 22 }
                  
      -- ********************************************************************************
      -- Blade Side Card VPD
      -- ********************************************************************************

      bladeSideCardVpdTable OBJECT-TYPE
                    SYNTAX  SEQUENCE OF BladeSideCardVpdEntry
                    MAX-ACCESS  not-accessible
                    STATUS  current -- was mandatory
                    DESCRIPTION
                    "Table of VPD information for the blade side card components.
                    For consistent results, view as a table and not as individual entries."
                    ::= { bladeHardwareVpd 4 }

      bladeSideCardVpdEntry OBJECT-TYPE
                    SYNTAX BladeSideCardVpdEntry
                    MAX-ACCESS  not-accessible
                    STATUS  current -- was mandatory
                    DESCRIPTION
                    "Blade side card VPD entry.
                    For consistent results, view as a table and not as individual entries."
                    INDEX { bladeSideCardVpdIndex }
                    ::= { bladeSideCardVpdTable 1 }

      BladeSideCardVpdEntry ::= SEQUENCE {
                  bladeSideCardVpdIndex INTEGER,
                  bladeSideCardVpdBayNumber OCTET STRING,
                  bladeSideCardVpdManufacturingId OCTET STRING,
                  bladeSideCardVpdFruNumber OCTET STRING,
                  bladeSideCardVpdHardwareRevision INTEGER,
                  bladeSideCardVpdSerialNumber OCTET STRING,
                  bladeSideCardVpdMachineType OCTET STRING,
                  bladeSideCardVpdUuid OCTET STRING,
                  bladeSideCardVpdManufDate OCTET STRING,
                  bladeSideCardVpdPartNumber OCTET STRING,
                  bladeSideCardVpdFruSerial OCTET STRING,
                  bladeSideCardVpdMachineModel OCTET STRING,
                  bladeSideCardVpdManufacturingIDNumber OCTET STRING,
                  bladeSideCardVpdProductId OCTET STRING,
                  bladeSideCardVpdSubManufacturerId OCTET STRING,
                  bladeSideCardVpdClei OCTET STRING,
                  bladeSideCardVpdBladeBayNumber OCTET STRING,
                  bladeSideCardVpdHardwareRevisionString OCTET STRING
                  }

      bladeSideCardVpdIndex  OBJECT-TYPE
                  SYNTAX  Integer32 (0..2147483647) -- was INTEGER
                  MAX-ACCESS  read-only
                  STATUS  current -- was mandatory
                  DESCRIPTION
                  "Blade side card VPD index.
                  For consistent results, view as a table and not as individual entries."
                  ::= { bladeSideCardVpdEntry 1 }

      bladeSideCardVpdBayNumber  OBJECT-TYPE
                  SYNTAX  OCTET STRING
                  MAX-ACCESS  read-only
                  STATUS  current -- was mandatory
                  DESCRIPTION
                  "Blade side card VPD Bay number.
                  For consistent results, view as a table and not as individual entries."
                  ::= { bladeSideCardVpdEntry 2 }

      bladeSideCardVpdManufacturingId  OBJECT-TYPE
                  SYNTAX  OCTET STRING
                  MAX-ACCESS  read-only
                  STATUS  current -- was mandatory
                  DESCRIPTION
                  "Blade side card VPD manufacturing ID.
                  For consistent results, view as a table and not as individual entries."
                  ::= { bladeSideCardVpdEntry 3 }

      bladeSideCardVpdFruNumber  OBJECT-TYPE
                  SYNTAX  OCTET STRING
                  MAX-ACCESS  read-only
                  STATUS  current -- was mandatory
                  DESCRIPTION
                  "Blade side card VPD FRU number.
                  For consistent results, view as a table and not as individual entries."
                  ::= { bladeSideCardVpdEntry 4 }


      bladeSideCardVpdHardwareRevision  OBJECT-TYPE
                  SYNTAX  INTEGER
                  MAX-ACCESS  read-only
                  STATUS  current -- was mandatory
                  DESCRIPTION
                  "Blade side card VPD hardware revision.
                  For consistent results, view as a table and not as individual entries.
                  If a hardware revision is programmed in the OEM VPD area for this component,
                  then the HardwareRevisionString version of this MIB object should be used."
                  ::= { bladeSideCardVpdEntry 5 }

      bladeSideCardVpdSerialNumber  OBJECT-TYPE
                  SYNTAX  OCTET STRING
                  MAX-ACCESS  read-only
                  STATUS  current -- was mandatory
                  DESCRIPTION
                  "Blade side card VPD serial number.
                  For consistent results, view as a table and not as individual entries."
                  ::= { bladeSideCardVpdEntry 6 }

      bladeSideCardVpdMachineType  OBJECT-TYPE
                  SYNTAX  OCTET STRING
                  MAX-ACCESS  read-only
                  STATUS  current -- was mandatory
                  DESCRIPTION
                  "Blade side card VPD machine type.
                  For consistent results, view as a table and not as individual entries."
                  ::= { bladeSideCardVpdEntry 7 }

      bladeSideCardVpdUuid  OBJECT-TYPE
                  SYNTAX  OCTET STRING
                  MAX-ACCESS  read-only
                  STATUS  current -- was mandatory
                  DESCRIPTION
                  "Blade side card VPD UUID.
                  For consistent results, view as a table and not as individual entries."
                  ::= { bladeSideCardVpdEntry 8 }

      bladeSideCardVpdManufDate  OBJECT-TYPE
                  SYNTAX  OCTET STRING
                  MAX-ACCESS  read-only
                  STATUS  current -- was mandatory
                  DESCRIPTION
                  "Blade side card VPD Manufacture Date.
                  For consistent results, view as a table and not as individual entries."
                  ::= { bladeSideCardVpdEntry 9 }

      bladeSideCardVpdPartNumber  OBJECT-TYPE
                  SYNTAX  OCTET STRING
                  MAX-ACCESS  read-only
                  STATUS  current -- was mandatory
                  DESCRIPTION
                  "Blade side card VPD Part number.
                  For consistent results, view as a table and not as individual entries."
                  ::= { bladeSideCardVpdEntry 10 }

      bladeSideCardVpdFruSerial  OBJECT-TYPE
                  SYNTAX  OCTET STRING
                  MAX-ACCESS  read-only
                  STATUS  current -- was mandatory
                  DESCRIPTION
                  "Blade side card VPD FRU serial number.
                  For consistent results, view as a table and not as individual entries."
                  ::= { bladeSideCardVpdEntry 11 }

       bladeSideCardVpdMachineModel  OBJECT-TYPE
                  SYNTAX  OCTET STRING
                  MAX-ACCESS  read-only
                  STATUS  current -- was mandatory
                  DESCRIPTION
                  "Blade side card VPD machine model.
                  For consistent results, view as a table and not as individual entries."
                  ::= { bladeSideCardVpdEntry 12 }

       bladeSideCardVpdManufacturingIDNumber  OBJECT-TYPE
                  SYNTAX  OCTET STRING
                  MAX-ACCESS  read-only
                  STATUS  current -- was mandatory
                  DESCRIPTION
                  "Blade side card VPD Manufacturer ID Number.
                  For consistent results, view as a table and not as individual entries."
                  ::= { bladeSideCardVpdEntry 13 }

       bladeSideCardVpdProductId  OBJECT-TYPE
                  SYNTAX  OCTET STRING
                  MAX-ACCESS  read-only
                  STATUS  current -- was mandatory
                  DESCRIPTION
                  "Blade side card VPD Product ID.
                  For consistent results, view as a table and not as individual entries."
                  ::= { bladeSideCardVpdEntry 14 }

       bladeSideCardVpdSubManufacturerId  OBJECT-TYPE
                  SYNTAX  OCTET STRING
                  MAX-ACCESS  read-only
                  STATUS  current -- was mandatory
                  DESCRIPTION
                  "Blade side card VPD subsystem manufacturer ID.
                  For consistent results, view as a table and not as individual entries."
                  ::= { bladeSideCardVpdEntry 15 }

       bladeSideCardVpdClei  OBJECT-TYPE
                  SYNTAX  OCTET STRING
                  MAX-ACCESS  read-only
                  STATUS  current -- was mandatory
                  DESCRIPTION
                  "Blade side card VPD Common Language
                  Equipment Identifier (CLEI).
                  For consistent results, view as a table and not as individual entries."
                  ::= { bladeSideCardVpdEntry 16 }

       bladeSideCardVpdBladeBayNumber  OBJECT-TYPE
                  SYNTAX  OCTET STRING
                  MAX-ACCESS  read-only
                  STATUS  current -- was mandatory
                  DESCRIPTION
                  "Blade bay number of the blade side card.  
                  For consistent results, view as a table and not as individual entries."
                  ::= { bladeSideCardVpdEntry 19 }
                  
      bladeSideCardVpdHardwareRevisionString  OBJECT-TYPE
                  SYNTAX  OCTET STRING
                  MAX-ACCESS  read-only
                  STATUS  current -- was mandatory
                  DESCRIPTION
                  "Blade side card VPD hardware revision in string format.
                  For consistent results, view as a table and not as individual entries.
                  If a hardware revision is programmed in the OEM VPD area for this component,
                  then this MIB object should be used."
                  ::= { bladeSideCardVpdEntry 20 }
                  
      -- ********************************************************************************
      -- Blade Expansion Card VPD
      -- ********************************************************************************

      bladeExpCardVpdTable OBJECT-TYPE
                    SYNTAX  SEQUENCE OF BladeExpCardVpdEntry
                    MAX-ACCESS  not-accessible
                    STATUS  current -- was mandatory
                    DESCRIPTION
                    "Table of VPD information for the blade expansion card components.
                    For consistent results, view as a table and not as individual entries."
                    ::= { bladeHardwareVpd 5 }

      bladeExpCardVpdEntry OBJECT-TYPE
                    SYNTAX BladeExpCardVpdEntry
                    MAX-ACCESS  not-accessible
                    STATUS  current -- was mandatory
                    DESCRIPTION
                    "Blade expansion card VPD entry.
                    For consistent results, view as a table and not as individual entries."
                    INDEX { bladeExpCardVpdIndex }
                    ::= { bladeExpCardVpdTable 1 }

      BladeExpCardVpdEntry ::= SEQUENCE {
                  bladeExpCardVpdIndex INTEGER,
                  bladeExpCardVpdBayNumber OCTET STRING,
                  bladeExpCardVpdManufacturingId OCTET STRING,
                  bladeExpCardVpdFruNumber OCTET STRING,
                  bladeExpCardVpdHardwareRevision INTEGER,
                  bladeExpCardVpdSerialNumber OCTET STRING,
                  bladeExpCardVpdMachineType OCTET STRING,
                  bladeExpCardVpdUuid OCTET STRING,
                  bladeExpCardVpdManufDate OCTET STRING,
                  bladeExpCardVpdPartNumber OCTET STRING,
                  bladeExpCardVpdFruSerial OCTET STRING,
                  bladeExpCardVpdMachineModel OCTET STRING,
                  bladeExpCardVpdManufacturingIDNumber OCTET STRING,
                  bladeExpCardVpdProductId OCTET STRING,
                  bladeExpCardVpdSubManufacturerId OCTET STRING,
                  bladeExpCardVpdClei OCTET STRING,
                  bladeExpCardVpdBladeBayNumber OCTET STRING,
                  bladeExpCardVpdCardTypeInfo INTEGER,
                  bladeExpCardVpdHighSpeed INTEGER,
                  bladeExpCardVpdHardwareRevisionString OCTET STRING
                  }

      bladeExpCardVpdIndex  OBJECT-TYPE
                  SYNTAX  Integer32 (0..2147483647) -- was INTEGER
                  MAX-ACCESS  read-only
                  STATUS  current -- was mandatory
                  DESCRIPTION
                  "Blade expansion card VPD index.
                  For consistent results, view as a table and not as individual entries."
                  ::= { bladeExpCardVpdEntry 1 }

      bladeExpCardVpdBayNumber  OBJECT-TYPE
                  SYNTAX  OCTET STRING
                  MAX-ACCESS  read-only
                  STATUS  current -- was mandatory
                  DESCRIPTION
                  "Blade expansion card VPD Bay number.
                  For consistent results, view as a table and not as individual entries."
                  ::= { bladeExpCardVpdEntry 2 }

      bladeExpCardVpdManufacturingId  OBJECT-TYPE
                  SYNTAX  OCTET STRING
                  MAX-ACCESS  read-only
                  STATUS  current -- was mandatory
                  DESCRIPTION
                  "Blade expansion card VPD manufacturing ID.
                  For consistent results, view as a table and not as individual entries."
                  ::= { bladeExpCardVpdEntry 3 }

      bladeExpCardVpdFruNumber  OBJECT-TYPE
                  SYNTAX  OCTET STRING
                  MAX-ACCESS  read-only
                  STATUS  current -- was mandatory
                  DESCRIPTION
                  "Blade expansion card VPD FRU number.
                  For consistent results, view as a table and not as individual entries."
                  ::= { bladeExpCardVpdEntry 4 }


      bladeExpCardVpdHardwareRevision  OBJECT-TYPE
                  SYNTAX  INTEGER
                  MAX-ACCESS  read-only
                  STATUS  current -- was mandatory
                  DESCRIPTION
                  "Blade expansion card VPD hardware revision.
                  For consistent results, view as a table and not as individual entries.
                  If a hardware revision is programmed in the OEM VPD area for this component,
                  then the HardwareRevisionString version of this MIB object should be used."
                  ::= { bladeExpCardVpdEntry 5 }

      bladeExpCardVpdSerialNumber  OBJECT-TYPE
                  SYNTAX  OCTET STRING
                  MAX-ACCESS  read-only
                  STATUS  current -- was mandatory
                  DESCRIPTION
                  "Blade expansion card VPD serial number.
                  For consistent results, view as a table and not as individual entries."
                  ::= { bladeExpCardVpdEntry 6 }

      bladeExpCardVpdMachineType  OBJECT-TYPE
                  SYNTAX  OCTET STRING
                  MAX-ACCESS  read-only
                  STATUS  current -- was mandatory
                  DESCRIPTION
                  "Blade expansion card VPD machine type.
                  For consistent results, view as a table and not as individual entries."
                  ::= { bladeExpCardVpdEntry 7 }

      bladeExpCardVpdUuid  OBJECT-TYPE
                  SYNTAX  OCTET STRING
                  MAX-ACCESS  read-only
                  STATUS  current -- was mandatory
                  DESCRIPTION
                  "Blade expansion card VPD UUID.
                  For consistent results, view as a table and not as individual entries."
                  ::= { bladeExpCardVpdEntry 8 }

      bladeExpCardVpdManufDate  OBJECT-TYPE
                  SYNTAX  OCTET STRING
                  MAX-ACCESS  read-only
                  STATUS  current -- was mandatory
                  DESCRIPTION
                  "Blade expansion card VPD Manufacture Date.
                  For consistent results, view as a table and not as individual entries."
                  ::= { bladeExpCardVpdEntry 9 }

      bladeExpCardVpdPartNumber  OBJECT-TYPE
                  SYNTAX  OCTET STRING
                  MAX-ACCESS  read-only
                  STATUS  current -- was mandatory
                  DESCRIPTION
                  "Blade expansion card VPD Part number.
                  For consistent results, view as a table and not as individual entries."
                  ::= { bladeExpCardVpdEntry 10 }

      bladeExpCardVpdFruSerial  OBJECT-TYPE
                  SYNTAX  OCTET STRING
                  MAX-ACCESS  read-only
                  STATUS  current -- was mandatory
                  DESCRIPTION
                  "Blade expansion card VPD FRU serial number.
                  For consistent results, view as a table and not as individual entries."
                  ::= { bladeExpCardVpdEntry 11 }

       bladeExpCardVpdMachineModel  OBJECT-TYPE
                  SYNTAX  OCTET STRING
                  MAX-ACCESS  read-only
                  STATUS  current -- was mandatory
                  DESCRIPTION
                  "Blade expansion card VPD machine model.
                  For consistent results, view as a table and not as individual entries."
                  ::= { bladeExpCardVpdEntry 12 }

      bladeExpCardVpdManufacturingIDNumber  OBJECT-TYPE
                  SYNTAX  OCTET STRING
                  MAX-ACCESS  read-only
                  STATUS  current -- was mandatory
                  DESCRIPTION
                  "Blade expansion card VPD Manufacturer ID Number.
                  For consistent results, view as a table and not as individual entries."
                  ::= { bladeExpCardVpdEntry 13 }

      bladeExpCardVpdProductId OBJECT-TYPE
                  SYNTAX  OCTET STRING
                  MAX-ACCESS  read-only
                  STATUS  current -- was mandatory
                  DESCRIPTION
                  "Blade expansion card VPD Product ID.
                  For consistent results, view as a table and not as individual entries."
                  ::= { bladeExpCardVpdEntry 14 }

      bladeExpCardVpdSubManufacturerId  OBJECT-TYPE
                  SYNTAX  OCTET STRING
                  MAX-ACCESS  read-only
                  STATUS  current -- was mandatory
                  DESCRIPTION
                  "Blade expansion card VPD subsystem manufacturer ID.
                  For consistent results, view as a table and not as individual entries."
                  ::= { bladeExpCardVpdEntry 15 }

      bladeExpCardVpdClei  OBJECT-TYPE
                  SYNTAX  OCTET STRING
                  MAX-ACCESS  read-only
                  STATUS  current -- was mandatory
                  DESCRIPTION
                  "Blade expansion card VPD Common Language Equipment Identifier (CLEI).
                  For consistent results, view as a table and not as individual entries."
                  ::= { bladeExpCardVpdEntry 16 }

       bladeExpCardVpdBladeBayNumber  OBJECT-TYPE
                  SYNTAX  OCTET STRING
                  MAX-ACCESS  read-only
                  STATUS  current -- was mandatory
                  DESCRIPTION
                  "Blade bay number of the blade expansion card.  
                  For consistent results, view as a table and not as individual entries."
                  ::= { bladeExpCardVpdEntry 19 }

       bladeExpCardVpdCardTypeInfo  OBJECT-TYPE
                  SYNTAX  INTEGER  {
                    unknown(0),
                    bladeEthernetExpCard(1),
                    bladeFiberChannelExpCard(2),
                    serialPortExpCard(3),
                    bladeOpticalPassThrough(4),
                    bladeInfinibandExpCard(5),
                    bladeIscsiExpCard(6),
                    bladeGenericExpCard(7),
                    bladeNetworkCFFeExpCard(8),
                    bladeSASConnectivityCard(9),
                    bladeSATAConnectivityCard(10),
                    bladeNetworkCFFzExpCard(11)
                  }
                  MAX-ACCESS  read-only
                  STATUS  current -- was mandatory
                  DESCRIPTION
                  "Blade expansion card (daughter card) VPD type code that describes the expansion 
                  card.  For consistent results, view as a table and not as individual entries.

                  NOTE: The CFFe expansion card is also referred to as a CFFh expansion card."
                  ::= { bladeExpCardVpdEntry 21 }
      
       bladeExpCardVpdHighSpeed  OBJECT-TYPE
                  SYNTAX  INTEGER  {
                    no(0),
                    yes(1), 
                    notApplicable(255)
                  }
                  MAX-ACCESS  read-only
                  STATUS  current -- was mandatory
                  DESCRIPTION
                  "Blade expansion card (daughter card) VPD high speed that indicates whether the  
                  expansion card is high speed or not.  For consistent results, view as a table and 
                  not as individual entries."
                  ::= { bladeExpCardVpdEntry 22 }
                  
      bladeExpCardVpdHardwareRevisionString  OBJECT-TYPE
                  SYNTAX  OCTET STRING
                  MAX-ACCESS  read-only
                  STATUS  current -- was mandatory
                  DESCRIPTION
                  "Blade expansion card VPD hardware revision in string format.
                  For consistent results, view as a table and not as individual entries.
                  If a hardware revision is programmed in the OEM VPD area for this component,
                  then this MIB object should be used."
                  ::= { bladeExpCardVpdEntry 23 }


      -- ********************************************************************************
      -- Blade cKVM card VPD
      -- ********************************************************************************

      bladecKVMCardVpdTable OBJECT-TYPE
                    SYNTAX  SEQUENCE OF BladecKVMCardVpdEntry
                    MAX-ACCESS  not-accessible
                    STATUS  current -- was mandatory
                    DESCRIPTION
                    "Table of VPD information for the blade
                    concurrent keyboard, video, and mouse (cKVM) card components.
                    For consistent results, view as a table and not as individual entries."
                    ::= { bladeHardwareVpd 6 }

      bladecKVMCardVpdEntry OBJECT-TYPE
                    SYNTAX BladecKVMCardVpdEntry
                    MAX-ACCESS  not-accessible
                    STATUS  current -- was mandatory
                    DESCRIPTION
                    "Blade concurrent keyboard, video, and mouse (cKVM) card VPD entry.
                    For consistent results, view as a table and not as individual entries."
                    INDEX { bladecKVMCardVpdIndex }
                    ::= { bladecKVMCardVpdTable 1 }

      BladecKVMCardVpdEntry ::= SEQUENCE {
                  bladecKVMCardVpdIndex INTEGER,
                  bladecKVMCardVpdBayNumber OCTET STRING,
                  bladecKVMCardVpdManufacturingId OCTET STRING,
                  bladecKVMCardVpdFruNumber OCTET STRING,
                  bladecKVMCardVpdHardwareRevision INTEGER,
                  bladecKVMCardVpdSerialNumber OCTET STRING,
                  bladecKVMCardVpdMachineType OCTET STRING,
                  bladecKVMCardVpdUuid OCTET STRING,
                  bladecKVMCardVpdManufDate OCTET STRING,
                  bladecKVMCardVpdPartNumber OCTET STRING,
                  bladecKVMCardVpdFruSerial OCTET STRING,
                  bladecKVMCardVpdMachineModel OCTET STRING,
                  bladecKVMCardVpdManufacturingIDNumber OCTET STRING,
                  bladecKVMCardVpdProductId OCTET STRING,
                  bladecKVMCardVpdSubManufacturerId OCTET STRING,
                  bladecKVMCardVpdClei OCTET STRING,
                  bladecKVMCardVpdHardwareRevisionString OCTET STRING
                  }

      bladecKVMCardVpdIndex  OBJECT-TYPE
                  SYNTAX  Integer32 (0..2147483647) -- was INTEGER
                  MAX-ACCESS  read-only
                  STATUS  current -- was mandatory
                  DESCRIPTION
                  "Blade concurrent keyboard mouse video (cKVM) card VPD index.
                  For consistent results, view as a table and not as individual entries."
                  ::= { bladecKVMCardVpdEntry 1 }

      bladecKVMCardVpdBayNumber  OBJECT-TYPE
                  SYNTAX  OCTET STRING
                  MAX-ACCESS  read-only
                  STATUS  current -- was mandatory
                  DESCRIPTION
                  "Blade concurrent keyboard video mouse (cKVM) card VPD Bay number.
                  For consistent results, view as a table and not as individual entries."
                  ::= { bladecKVMCardVpdEntry 2 }

      bladecKVMCardVpdManufacturingId  OBJECT-TYPE
                  SYNTAX  OCTET STRING
                  MAX-ACCESS  read-only
                  STATUS  current -- was mandatory
                  DESCRIPTION
                  "Blade concurrent keyboard video mouse (cKVM) card VPD manufacturing ID.
                  For consistent results, view as a table and not as individual entries."
                  ::= { bladecKVMCardVpdEntry 3 }

      bladecKVMCardVpdFruNumber  OBJECT-TYPE
                  SYNTAX  OCTET STRING
                  MAX-ACCESS  read-only
                  STATUS  current -- was mandatory
                  DESCRIPTION
                  "Blade concurrent keyboard video mouse (cKVM) card VPD FRU number.
                  For consistent results, view as a table and not as individual entries."
                  ::= { bladecKVMCardVpdEntry 4 }


      bladecKVMCardVpdHardwareRevision  OBJECT-TYPE
                  SYNTAX  INTEGER
                  MAX-ACCESS  read-only
                  STATUS  current -- was mandatory
                  DESCRIPTION
                  "Blade concurrent keyboard video mouse (cKVM) card VPD hardware revision.
                  For consistent results, view as a table and not as individual entries.
                  If a hardware revision is programmed in the OEM VPD area for this component,
                  then the HardwareRevisionString version of this MIB object should be used."
                  ::= { bladecKVMCardVpdEntry 5 }

      bladecKVMCardVpdSerialNumber  OBJECT-TYPE
                  SYNTAX  OCTET STRING
                  MAX-ACCESS  read-only
                  STATUS  current -- was mandatory
                  DESCRIPTION
                  "Blade concurrent keyboard video mouse (cKVM) card VPD serial number.
                  For consistent results, view as a table and not as individual entries."
                  ::= { bladecKVMCardVpdEntry 6 }

      bladecKVMCardVpdMachineType  OBJECT-TYPE
                  SYNTAX  OCTET STRING
                  MAX-ACCESS  read-only
                  STATUS  current -- was mandatory
                  DESCRIPTION
                  "Blade concurrent keyboard video mouse (cKVM) card VPD machine type.
                  For consistent results, view as a table and not as individual entries."
                  ::= { bladecKVMCardVpdEntry 7 }

      bladecKVMCardVpdUuid  OBJECT-TYPE
                  SYNTAX  OCTET STRING
                  MAX-ACCESS  read-only
                  STATUS  current -- was mandatory
                  DESCRIPTION
                  "Blade concurrent keyboard video mouse (cKVM) card VPD UUID.
                  For consistent results, view as a table and not as individual entries."
                  ::= { bladecKVMCardVpdEntry 8 }

      bladecKVMCardVpdManufDate  OBJECT-TYPE
                  SYNTAX  OCTET STRING
                  MAX-ACCESS  read-only
                  STATUS  current -- was mandatory
                  DESCRIPTION
                  "Blade concurrent keyboard video mouse (cKVM) card VPD Manufacture Date.
                  For consistent results, view as a table and not as individual entries."
                  ::= { bladecKVMCardVpdEntry 9 }

      bladecKVMCardVpdPartNumber  OBJECT-TYPE
                  SYNTAX  OCTET STRING
                  MAX-ACCESS  read-only
                  STATUS  current -- was mandatory
                  DESCRIPTION
                  "Blade concurrent keyboard video mouse (cKVM) card VPD Part number.
                  For consistent results, view as a table and not as individual entries."
                  ::= { bladecKVMCardVpdEntry 10 }

      bladecKVMCardVpdFruSerial  OBJECT-TYPE
                  SYNTAX  OCTET STRING
                  MAX-ACCESS  read-only
                  STATUS  current -- was mandatory
                  DESCRIPTION
                  "Blade concurrent keyboard video mouse (cKVM) card VPD FRU serial number.
                  For consistent results, view as a table and not as individual entries."
                  ::= { bladecKVMCardVpdEntry 11 }

       bladecKVMCardVpdMachineModel  OBJECT-TYPE
                  SYNTAX  OCTET STRING
                  MAX-ACCESS  read-only
                  STATUS  current -- was mandatory
                  DESCRIPTION
                  "Blade concurrent keyboard video mouse (cKVM) card VPD machine model.
                  For consistent results, view as a table and not as individual entries."
                  ::= { bladecKVMCardVpdEntry 12 }

      bladecKVMCardVpdManufacturingIDNumber OBJECT-TYPE
                  SYNTAX  OCTET STRING
                  MAX-ACCESS  read-only
                  STATUS  current -- was mandatory
                  DESCRIPTION
                  "Blade concurrent keyboard video mouse (cKVM) card VPD 
                  manufacturer ID.
                  For consistent results, view as a table and not as individual entries."
                  ::= { bladecKVMCardVpdEntry 13 }

      bladecKVMCardVpdProductId  OBJECT-TYPE
                  SYNTAX  OCTET STRING
                  MAX-ACCESS  read-only
                  STATUS  current -- was mandatory
                  DESCRIPTION
                  "Blade concurrent keyboard video mouse (cKVM) card VPD 
                  Product ID.
                  For consistent results, view as a table and not as individual entries."
                  ::= { bladecKVMCardVpdEntry 14 }

      bladecKVMCardVpdSubManufacturerId  OBJECT-TYPE
                  SYNTAX  OCTET STRING
                  MAX-ACCESS  read-only
                  STATUS  current -- was mandatory
                  DESCRIPTION
                  "Blade concurrent keyboard video mouse (cKVM) card VPD 
                  subsystem manufacturer ID.
                  For consistent results, view as a table and not as individual entries."
                  ::= { bladecKVMCardVpdEntry 15 }

      bladecKVMCardVpdClei  OBJECT-TYPE
                  SYNTAX  OCTET STRING
                  MAX-ACCESS  read-only
                  STATUS  current -- was mandatory
                  DESCRIPTION
                  "Blade concurrent keyboard video mouse (cKVM) card VPD 
                  Common Language Equipment Identifier (CLEI).
                  For consistent results, view as a table and not as individual entries."
                  ::= { bladecKVMCardVpdEntry 16 }

      bladecKVMCardVpdHardwareRevisionString  OBJECT-TYPE
                  SYNTAX  OCTET STRING
                  MAX-ACCESS  read-only
                  STATUS  current -- was mandatory
                  DESCRIPTION
                  "Blade concurrent keyboard video mouse (cKVM) card VPD hardware revision in string format.
                  For consistent results, view as a table and not as individual entries.
                  If a hardware revision is programmed in the OEM VPD area for this component,
                  then this MIB object should be used."
                  ::= { bladecKVMCardVpdEntry 17 }
                  
      -- ********************************************************************************
      -- Table for the blade and expansion card WWN/GUIDs
      -- ********************************************************************************
        bladeAndExpCardWwnGuidVpdTable OBJECT-TYPE
                    SYNTAX  SEQUENCE OF BladeAndExpCardWwnGuidVpdEntry
                    MAX-ACCESS  not-accessible
                    STATUS  current -- was mandatory
                    DESCRIPTION
                    "Table of World Wide Names (WWN), Global Unique IDs (GUID) and
                    Serial Attach SCSI IDs (SAS) of the blade server and its expansion
                    cards (daughter cards).
                    For consistent results, view as a table and not as individual entries."
                    ::= { bladeHardwareVpd 7 }

        bladeAndExpCardWwnGuidVpdEntry OBJECT-TYPE
                    SYNTAX  BladeAndExpCardWwnGuidVpdEntry
                    MAX-ACCESS  not-accessible
                    STATUS  current -- was mandatory
                    DESCRIPTION
                    "Blade WWN/GUID entries.  
                    For consistent results, view as a table and not as individual entries."
                    INDEX { bladeAndExpCardWwnGuidVpdIndex }
                    ::= { bladeAndExpCardWwnGuidVpdTable 1 }

        BladeAndExpCardWwnGuidVpdEntry ::= SEQUENCE {
                    bladeAndExpCardWwnGuidVpdIndex INTEGER,
                    bladeAndExpCardWwnGuidVpdBayNumber OCTET STRING,
                    bladeAndExpCardWwnGuidVpdName OCTET STRING,
                    bladeAndExpCardWwnGuidVpdBladeBayNumber OCTET STRING,
                    bladeAndExpCardWwnGuidVpdType INTEGER,
                    bladeAndExpCardWwnGuidVpd1 OCTET STRING,
                    bladeAndExpCardWwnGuidVpd2 OCTET STRING,
                    bladeAndExpCardWwnGuidVpd3 OCTET STRING,
                    bladeAndExpCardWwnGuidVpd4 OCTET STRING,
                    bladeAndExpCardWwnGuidVpd5 OCTET STRING,
                    bladeAndExpCardWwnGuidVpd6 OCTET STRING,
                    bladeAndExpCardWwnGuidVpd7 OCTET STRING,
                    bladeAndExpCardWwnGuidVpd8 OCTET STRING
                    }

        bladeAndExpCardWwnGuidVpdIndex  OBJECT-TYPE
                    SYNTAX  Integer32 (0..2147483647) -- was INTEGER
                    MAX-ACCESS  read-only
                    STATUS  current -- was mandatory
                    DESCRIPTION
                    "Blade or expansion card index.  
                    For consistent results, view as a table and not as individual entries."
                    ::= { bladeAndExpCardWwnGuidVpdEntry 1 }

        bladeAndExpCardWwnGuidVpdBayNumber  OBJECT-TYPE
                    SYNTAX  OCTET STRING
                    MAX-ACCESS  read-only
                    STATUS  current -- was mandatory
                    DESCRIPTION
                    "Blade or expansion card VPD bay number.  
                    For consistent results, view as a table and not as individual entries."
                    ::= { bladeAndExpCardWwnGuidVpdEntry 2 }

        bladeAndExpCardWwnGuidVpdName  OBJECT-TYPE
                    SYNTAX  OCTET STRING
                    MAX-ACCESS  read-only
                    STATUS  current -- was mandatory
                    DESCRIPTION
                    "The name of the blade or expansion card.  
                    For consistent results, view as a table and not as individual entries."
                    ::= { bladeAndExpCardWwnGuidVpdEntry 3 }

        bladeAndExpCardWwnGuidVpdBladeBayNumber  OBJECT-TYPE
                    SYNTAX  OCTET STRING
                    MAX-ACCESS  read-only
                    STATUS  current -- was mandatory
                    DESCRIPTION
                    "For expansion cards, it's the blade bay number of the blade 
                    expansion card. For blades, it's the bay number of the blade. 
                    For consistent results, view as a table and not as individual entries."
                    ::= { bladeAndExpCardWwnGuidVpdEntry 4 }

        bladeAndExpCardWwnGuidVpdType  OBJECT-TYPE
                    SYNTAX  INTEGER  {
                      notAvailable(0),
                      wwn(1),
                      guid(2),
                      sas(3)
                    }
                    MAX-ACCESS  read-only
                    STATUS  current -- was mandatory
                    DESCRIPTION
                    "Blade or expansion card WWN/GUID/SAS Type.  
                    For consistent results, view as a table and not as individual entries."
                    ::= { bladeAndExpCardWwnGuidVpdEntry 5 }

        bladeAndExpCardWwnGuidVpd1  OBJECT-TYPE
                    SYNTAX  OCTET STRING
                    MAX-ACCESS  read-only
                    STATUS  current -- was mandatory
                    DESCRIPTION
                    "Blade or expansion card WWN/GUID 1.  
                    For consistent results, view as a table and not as individual entries."
                    ::= { bladeAndExpCardWwnGuidVpdEntry 6 }

        bladeAndExpCardWwnGuidVpd2  OBJECT-TYPE
                    SYNTAX  OCTET STRING
                    MAX-ACCESS  read-only
                    STATUS  current -- was mandatory
                    DESCRIPTION
                    "Blade or expansion card WWN/GUID 2.  
                    For consistent results, view as a table and not as individual entries."
                    ::= { bladeAndExpCardWwnGuidVpdEntry 7 }

        bladeAndExpCardWwnGuidVpd3  OBJECT-TYPE
                    SYNTAX  OCTET STRING
                    MAX-ACCESS  read-only
                    STATUS  current -- was mandatory
                    DESCRIPTION
                    "Blade or expansion card WWN/GUID 3.  
                    For consistent results, view as a table and not as individual entries."
                    ::= { bladeAndExpCardWwnGuidVpdEntry 8 }

        bladeAndExpCardWwnGuidVpd4  OBJECT-TYPE
                    SYNTAX  OCTET STRING
                    MAX-ACCESS  read-only
                    STATUS  current -- was mandatory
                    DESCRIPTION
                    "Blade or expansion card WWN/GUID 4.  
                    For consistent results, view as a table and not as individual entries."
                    ::= { bladeAndExpCardWwnGuidVpdEntry 9 }

        bladeAndExpCardWwnGuidVpd5  OBJECT-TYPE
                    SYNTAX  OCTET STRING
                    MAX-ACCESS  read-only
                    STATUS  current -- was mandatory
                    DESCRIPTION
                    "Blade or expansion card WWN/GUID 5.  
                    For consistent results, view as a table and not as individual entries."
                    ::= { bladeAndExpCardWwnGuidVpdEntry 10 }

        bladeAndExpCardWwnGuidVpd6  OBJECT-TYPE
                    SYNTAX  OCTET STRING
                    MAX-ACCESS  read-only
                    STATUS  current -- was mandatory
                    DESCRIPTION
                    "Blade or expansion card WWN/GUID 6.  
                    For consistent results, view as a table and not as individual entries."
                    ::= { bladeAndExpCardWwnGuidVpdEntry 11 }

        bladeAndExpCardWwnGuidVpd7  OBJECT-TYPE
                    SYNTAX  OCTET STRING
                    MAX-ACCESS  read-only
                    STATUS  current -- was mandatory
                    DESCRIPTION
                    "Blade or expansion card WWN/GUID 7.  
                    For consistent results, view as a table and not as individual entries."
                    ::= { bladeAndExpCardWwnGuidVpdEntry 12 }

        bladeAndExpCardWwnGuidVpd8  OBJECT-TYPE
                    SYNTAX  OCTET STRING
                    MAX-ACCESS  read-only
                    STATUS  current -- was mandatory
                    DESCRIPTION
                    "Blade or expansion card WWN/GUID 8.  
                    For consistent results, view as a table and not as individual entries."
                    ::= { bladeAndExpCardWwnGuidVpdEntry 13 }


      -- ********************************************************************************
      -- Blade managerment card vpd
      -- ********************************************************************************

      bladeManagementCardVpdTable OBJECT-TYPE
                    SYNTAX  SEQUENCE OF BladeManagementCardVpdEntry
                    MAX-ACCESS  not-accessible
                    STATUS  current -- was mandatory
                    DESCRIPTION
                    "Table of VPD information for the blade
                    management card component.
                    For consistent results, view as a table 
                    and not as individual entries."
                    ::= { bladeHardwareVpd 8 }

      bladeManagementCardVpdEntry OBJECT-TYPE
                    SYNTAX  BladeManagementCardVpdEntry
                    MAX-ACCESS  not-accessible
                    STATUS  current -- was mandatory
                    DESCRIPTION
                    "Blade management card VPD entry.
                    For consistent results, view as a table 
                    and not as individual entries."
                    INDEX { bladeManagementCardVpdIndex }
                    ::= { bladeManagementCardVpdTable 1 }

      BladeManagementCardVpdEntry ::= SEQUENCE {
                  bladeManagementCardVpdIndex INTEGER,
                  bladeManagementCardVpdBayNumber OCTET STRING,
                  bladeManagementCardVpdManufacturingId OCTET STRING,
                  bladeManagementCardVpdFruNumber OCTET STRING,
                  bladeManagementCardVpdHardwareRevision INTEGER,
                  bladeManagementCardVpdSerialNumber OCTET STRING,
                  bladeManagementCardVpdMachineType OCTET STRING,
                  bladeManagementCardVpdUuid OCTET STRING,
                  bladeManagementCardVpdManufDate OCTET STRING,
                  bladeManagementCardVpdPartNumber OCTET STRING,
                  bladeManagementCardVpdFruSerial OCTET STRING,
                  bladeManagementCardVpdMachineModel OCTET STRING,
                  bladeManagementCardVpdManufacturingIDNumber OCTET STRING,
                  bladeManagementCardVpdProductId OCTET STRING,
                  bladeManagementCardVpdSubManufacturerId OCTET STRING,
                  bladeManagementCardVpdClei OCTET STRING,
                  bladeManagementCardVpdHardwareRevisionString OCTET STRING
                  }

      bladeManagementCardVpdIndex  OBJECT-TYPE
                  SYNTAX  Integer32 (0..2147483647) -- was INTEGER
                  MAX-ACCESS  read-only
                  STATUS  current -- was mandatory
                  DESCRIPTION
                  "Blade management card VPD index.
                  For consistent results, view as a table 
                  and not as individual entries."
                  ::= { bladeManagementCardVpdEntry 1 }

      bladeManagementCardVpdBayNumber  OBJECT-TYPE
                  SYNTAX  OCTET STRING
                  MAX-ACCESS  read-only
                  STATUS  current -- was mandatory
                  DESCRIPTION
                  "Blade management card VPD Bay number.
                  For consistent results, view as a table and 
                  not as individual entries."
                  ::= { bladeManagementCardVpdEntry 2 }

      bladeManagementCardVpdManufacturingId  OBJECT-TYPE
                  SYNTAX  OCTET STRING
                  MAX-ACCESS  read-only
                  STATUS  current -- was mandatory
                  DESCRIPTION
                  "Blade management card VPD manufacturing ID.
                  For consistent results, view as a table and not as 
                  individual entries."
                  ::= { bladeManagementCardVpdEntry 3 }
      bladeManagementCardVpdFruNumber  OBJECT-TYPE
                  SYNTAX  OCTET STRING
                  MAX-ACCESS  read-only
                  STATUS  current -- was mandatory
                  DESCRIPTION
                  "Blade management card VPD FRU number.
                  For consistent results, view as a table and not 
                  as individual entries."
                  ::= { bladeManagementCardVpdEntry 4 }


      bladeManagementCardVpdHardwareRevision  OBJECT-TYPE
                  SYNTAX  INTEGER
                  MAX-ACCESS  read-only
                  STATUS  current -- was mandatory
                  DESCRIPTION
                  "Blade management card VPD hardware revision.
                  For consistent results, view as a table and not as 
                  individual entries.
                  If a hardware revision is programmed in the OEM VPD area for this component,
                  then the HardwareRevisionString version of this MIB object should be used."
                  ::= { bladeManagementCardVpdEntry 5 }
                  
      bladeManagementCardVpdSerialNumber  OBJECT-TYPE
                  SYNTAX  OCTET STRING
                  MAX-ACCESS  read-only
                  STATUS  current -- was mandatory
                  DESCRIPTION
                  "Blade management card VPD serial number.
                  For consistent results, view as a table and not 
                  as individual entries."
                  ::= { bladeManagementCardVpdEntry 6 }

      bladeManagementCardVpdMachineType  OBJECT-TYPE
                  SYNTAX  OCTET STRING
                  MAX-ACCESS  read-only
                  STATUS  current -- was mandatory
                  DESCRIPTION
                  "Blade management card VPD machine type.
                  For consistent results, view as a table and not 
                  as individual entries."
                  ::= { bladeManagementCardVpdEntry 7 }

      bladeManagementCardVpdUuid  OBJECT-TYPE
                  SYNTAX  OCTET STRING
                  MAX-ACCESS  read-only
                  STATUS  current -- was mandatory
                  DESCRIPTION
                  "Blade management card VPD UUID.
                  For consistent results, view as a table 
                  and not as individual entries."
                  ::= { bladeManagementCardVpdEntry 8 }
      bladeManagementCardVpdManufDate  OBJECT-TYPE
                  SYNTAX  OCTET STRING
                  MAX-ACCESS  read-only
                  STATUS  current -- was mandatory
                  DESCRIPTION
                  "Blade management card VPD Manufacture Date.
                  For consistent results, view as a table and not as 
                  individual entries."
                  ::= { bladeManagementCardVpdEntry 9 }
      bladeManagementCardVpdPartNumber  OBJECT-TYPE
                  SYNTAX  OCTET STRING
                  MAX-ACCESS  read-only
                  STATUS  current -- was mandatory
                  DESCRIPTION
                  "Blade management card VPD Part number.
                  For consistent results, view as a table and not 
                  as individual entries."
                  ::= { bladeManagementCardVpdEntry 10 }

      bladeManagementCardVpdFruSerial  OBJECT-TYPE
                  SYNTAX  OCTET STRING
                  MAX-ACCESS  read-only
                  STATUS  current -- was mandatory
                  DESCRIPTION
                  "Blade management card VPD FRU serial number.
                  For consistent results, view as a table and not as 
                  individual entries."
                  ::= { bladeManagementCardVpdEntry 11 }

       bladeManagementCardVpdMachineModel  OBJECT-TYPE
                  SYNTAX  OCTET STRING
                  MAX-ACCESS  read-only
                  STATUS  current -- was mandatory
                  DESCRIPTION
                  "Blade management card VPD machine model.
                  For consistent results, view as a table and not 
                  as individual entries."
                  ::= { bladeManagementCardVpdEntry 12 }

      bladeManagementCardVpdManufacturingIDNumber OBJECT-TYPE
                  SYNTAX  OCTET STRING
                  MAX-ACCESS  read-only
                  STATUS  current -- was mandatory
                  DESCRIPTION
                  "Blade management card VPD manufacturer ID.
                  For consistent results, view as a table and not as 
                  individual entries."
                  ::= { bladeManagementCardVpdEntry 13 }

      bladeManagementCardVpdProductId  OBJECT-TYPE
                  SYNTAX  OCTET STRING
                  MAX-ACCESS  read-only
                  STATUS  current -- was mandatory
                  DESCRIPTION
                  "Blade management card VPD Product ID.
                  For consistent results, view as a table and not 
                  as individual entries."
                  ::= { bladeManagementCardVpdEntry 14 }

      bladeManagementCardVpdSubManufacturerId  OBJECT-TYPE
                  SYNTAX  OCTET STRING
                  MAX-ACCESS  read-only
                  STATUS  current -- was mandatory
                  DESCRIPTION
                  "Blade management card VPD subsystem manufacturer ID.
                  For consistent results, view as a table and not as 
                  individual entries."
                  ::= { bladeManagementCardVpdEntry 15 }

      bladeManagementCardVpdClei  OBJECT-TYPE
                  SYNTAX  OCTET STRING
                  MAX-ACCESS  read-only
                  STATUS  current -- was mandatory
                  DESCRIPTION
                  "Blade management card VPD Common Language Equipment 
                  Identifier (CLEI).
                  For consistent results, view as a table and not as 
                  individual entries."
                  ::= { bladeManagementCardVpdEntry 16 }

      bladeManagementCardVpdHardwareRevisionString  OBJECT-TYPE
                  SYNTAX  OCTET STRING
                  MAX-ACCESS  read-only
                  STATUS  current -- was mandatory
                  DESCRIPTION
                  "Blade management card VPD hardware revision in string format.
                  For consistent results, view as a table and not as 
                  individual entries.
                  If a hardware revision is programmed in the OEM VPD area for this component,
                  then this MIB object should be used."
                  ::= { bladeManagementCardVpdEntry 17 }

      -- ********************************************************************************
      -- System Firmware Level VPD
      -- ********************************************************************************
      bladeFirmwareVpd OBJECT IDENTIFIER ::= { vpdInformation 5 }


       bladeBiosVPDTable OBJECT-TYPE
                      SYNTAX  SEQUENCE OF BladeBiosVPDEntry
                      MAX-ACCESS  not-accessible
                      STATUS  current -- was mandatory
                      DESCRIPTION
                      "Table of blade firmware vital product data (VPD) information."
                      ::= { bladeFirmwareVpd 1 }

        bladeBiosVPDEntry OBJECT-TYPE
                      SYNTAX BladeBiosVPDEntry
                      MAX-ACCESS  not-accessible
                      STATUS  current -- was mandatory
                      DESCRIPTION
                      "Blade firmware VPD table entry"
                      INDEX { bladeBiosVpdIndex }
                      ::= { bladeBiosVPDTable 1 }


        BladeBiosVPDEntry ::= SEQUENCE {
                    bladeBiosVpdIndex INTEGER,
                    bladeBiosVpdId INTEGER,
                    bladeBiosVpdExists INTEGER,
                    bladeBiosVpdPowerState INTEGER,
                    bladeBiosVpdName OCTET STRING,
                    bladeBiosVpdBuildId OCTET STRING,
                    bladeBiosVpdRevision OCTET STRING,
                    bladeBiosVpdDate OCTET STRING
                    }

        bladeBiosVpdIndex  OBJECT-TYPE
                    SYNTAX  Integer32 (0..2147483647) -- was INTEGER
                    MAX-ACCESS  read-only
                    STATUS  current -- was mandatory
                    DESCRIPTION
                    "Blade firmware VPD table index."
                    ::= { bladeBiosVPDEntry 1 }


        bladeBiosVpdId  OBJECT-TYPE
                    SYNTAX  INTEGER {
                      blade1(1),
                      blade2(2),
                      blade3(3),
                      blade4(4),
                      blade5(5),
                      blade6(6),
                      blade7(7),
                      blade8(8),
                      blade9(9),
                      blade10(10),
                      blade11(11),
                      blade12(12),
                      blade13(13),
                      blade14(14)
                    }
                    MAX-ACCESS  read-only
                    STATUS  current -- was mandatory
                    DESCRIPTION
                    "The numeric blade ID."
                    ::= { bladeBiosVPDEntry 2 }

        bladeBiosVpdExists OBJECT-TYPE
                    SYNTAX  INTEGER {
                      false(0),
                      true(1)
                    }
                    MAX-ACCESS  read-only
                    STATUS  current -- was mandatory
                    DESCRIPTION
                    "Indicates whether the server blade specified exists or not."
                    ::= { bladeBiosVPDEntry 3 }

        bladeBiosVpdPowerState OBJECT-TYPE
                    SYNTAX  INTEGER {
                      off(0),
                      on(1),
                      standby(3),
                      hibernate(4)
                    }
                    MAX-ACCESS  read-only
                    STATUS  current -- was mandatory
                    DESCRIPTION
                    "Indicates the power state of the blade specified."
                    ::= { bladeBiosVPDEntry 4 }

        bladeBiosVpdName OBJECT-TYPE
                    SYNTAX  OCTET STRING
                    MAX-ACCESS  read-only
                    STATUS  current -- was mandatory
                    DESCRIPTION
                    "The name of the blade as a null terminated string."
                    ::= { bladeBiosVPDEntry 5 }

        bladeBiosVpdBuildId OBJECT-TYPE
                    SYNTAX  OCTET STRING
                    MAX-ACCESS  read-only
                    STATUS  current -- was mandatory
                    DESCRIPTION
                    "The build ID for the blade firmware."
                    ::= { bladeBiosVPDEntry 6 }

        bladeBiosVpdRevision OBJECT-TYPE
                    SYNTAX  OCTET STRING
                    MAX-ACCESS  read-only
                    STATUS  current -- was mandatory
                    DESCRIPTION
                    "The revision of the blade firmware."
                    ::= { bladeBiosVPDEntry 7 }

        bladeBiosVpdDate OBJECT-TYPE
                    SYNTAX  OCTET STRING
                    MAX-ACCESS  read-only
                    STATUS  current -- was mandatory
                    DESCRIPTION
                    "The date of the blade firmware."
                    ::= { bladeBiosVPDEntry 8 }



       bladeDiagsVPDTable OBJECT-TYPE
                      SYNTAX  SEQUENCE OF BladeDiagsVPDEntry
                      MAX-ACCESS  not-accessible
                      STATUS  current -- was mandatory
                      DESCRIPTION
                      "Table of blade firmware vital product data (VPD) information."
                      ::= { bladeFirmwareVpd 2 }

        bladeDiagsVPDEntry OBJECT-TYPE
                      SYNTAX BladeDiagsVPDEntry
                      MAX-ACCESS  not-accessible
                      STATUS  current -- was mandatory
                      DESCRIPTION
                      "Blade firmware VPD table entry"
                      INDEX { bladeDiagsVpdIndex }
                      ::= { bladeDiagsVPDTable 1 }


        BladeDiagsVPDEntry ::= SEQUENCE {
                    bladeDiagsVpdIndex INTEGER,
                    bladeDiagsVpdId INTEGER,
                    bladeDiagsVpdExists INTEGER,
                    bladeDiagsVpdPowerState INTEGER,
                    bladeDiagsVpdName OCTET STRING,
                    bladeDiagsVpdBuildId OCTET STRING,
                    bladeDiagsVpdRevision OCTET STRING,
                    bladeDiagsVpdDate OCTET STRING
                    }

        bladeDiagsVpdIndex  OBJECT-TYPE
                    SYNTAX  Integer32 (0..2147483647) -- was INTEGER
                    MAX-ACCESS  read-only
                    STATUS  current -- was mandatory
                    DESCRIPTION
                    "Blade firmware VPD table index."
                    ::= { bladeDiagsVPDEntry 1 }


        bladeDiagsVpdId  OBJECT-TYPE
                    SYNTAX  INTEGER {
                      blade1(1),
                      blade2(2),
                      blade3(3),
                      blade4(4),
                      blade5(5),
                      blade6(6),
                      blade7(7),
                      blade8(8),
                      blade9(9),
                      blade10(10),
                      blade11(11),
                      blade12(12),
                      blade13(13),
                      blade14(14)
                    }
                    MAX-ACCESS  read-only
                    STATUS  current -- was mandatory
                    DESCRIPTION
                    "The numeric blade ID."
                    ::= { bladeDiagsVPDEntry 2 }

        bladeDiagsVpdExists OBJECT-TYPE
                    SYNTAX  INTEGER {
                      false(0),
                      true(1)
                    }
                    MAX-ACCESS  read-only
                    STATUS  current -- was mandatory
                    DESCRIPTION
                    "Indicates whether the server blade specified exists or not."
                    ::= { bladeDiagsVPDEntry 3 }

        bladeDiagsVpdPowerState OBJECT-TYPE
                    SYNTAX  INTEGER {
                      off(0),
                      on(1),
                      standby(3),
                      hibernate(4)                      
                    }
                    MAX-ACCESS  read-only
                    STATUS  current -- was mandatory
                    DESCRIPTION
                    "Indicates the power state of the blade specified."
                    ::= { bladeDiagsVPDEntry 4 }

        bladeDiagsVpdName OBJECT-TYPE
                    SYNTAX  OCTET STRING
                    MAX-ACCESS  read-only
                    STATUS  current -- was mandatory
                    DESCRIPTION
                    "The name of the blade as a null terminated string."
                    ::= { bladeDiagsVPDEntry 5 }

        bladeDiagsVpdBuildId OBJECT-TYPE
                    SYNTAX  OCTET STRING
                    MAX-ACCESS  read-only
                    STATUS  current -- was mandatory
                    DESCRIPTION
                    "The build ID for the blade firmware."
                    ::= { bladeDiagsVPDEntry 6 }

        bladeDiagsVpdRevision OBJECT-TYPE
                    SYNTAX  OCTET STRING
                    MAX-ACCESS  read-only
                    STATUS  current -- was mandatory
                    DESCRIPTION
                    "The revision of the blade firmware."
                    ::= { bladeDiagsVPDEntry 7 }

        bladeDiagsVpdDate OBJECT-TYPE
                    SYNTAX  OCTET STRING
                    MAX-ACCESS  read-only
                    STATUS  current -- was mandatory
                    DESCRIPTION
                    "The date of the blade firmware."
                    ::= { bladeDiagsVPDEntry 8 }




       bladeSysMgmtProcVPDTable OBJECT-TYPE
                      SYNTAX  SEQUENCE OF BladeSysMgmtProcVPDEntry
                      MAX-ACCESS  not-accessible
                      STATUS  current -- was mandatory
                      DESCRIPTION
                      "Table of blade firmware vital product data (VPD) information."
                      ::= { bladeFirmwareVpd 3 }

        bladeSysMgmtProcVPDEntry OBJECT-TYPE
                      SYNTAX BladeSysMgmtProcVPDEntry
                      MAX-ACCESS  not-accessible
                      STATUS  current -- was mandatory
                      DESCRIPTION
                      "Blade firmware VPD table entry"
                      INDEX { bladeSysMgmtProcVpdIndex }
                      ::= { bladeSysMgmtProcVPDTable 1 }


        BladeSysMgmtProcVPDEntry ::= SEQUENCE {
                    bladeSysMgmtProcVpdIndex INTEGER,
                    bladeSysMgmtProcVpdId INTEGER,
                    bladeSysMgmtProcVpdExists INTEGER,
                    bladeSysMgmtProcVpdPowerState INTEGER,
                    bladeSysMgmtProcVpdName OCTET STRING,
                    bladeSysMgmtProcVpdBuildId OCTET STRING,
                    bladeSysMgmtProcVpdRevision OCTET STRING
                    }

        bladeSysMgmtProcVpdIndex  OBJECT-TYPE
                    SYNTAX  Integer32 (0..2147483647) -- was INTEGER
                    MAX-ACCESS  read-only
                    STATUS  current -- was mandatory
                    DESCRIPTION
                    "Blade firmware VPD table index."
                    ::= { bladeSysMgmtProcVPDEntry 1 }


        bladeSysMgmtProcVpdId  OBJECT-TYPE
                    SYNTAX  INTEGER {
                      blade1(1),
                      blade2(2),
                      blade3(3),
                      blade4(4),
                      blade5(5),
                      blade6(6),
                      blade7(7),
                      blade8(8),
                      blade9(9),
                      blade10(10),
                      blade11(11),
                      blade12(12),
                      blade13(13),
                      blade14(14)
                    }
                    MAX-ACCESS  read-only
                    STATUS  current -- was mandatory
                    DESCRIPTION
                    "The numeric blade ID."
                    ::= { bladeSysMgmtProcVPDEntry 2 }

        bladeSysMgmtProcVpdExists OBJECT-TYPE
                    SYNTAX  INTEGER {
                      false(0),
                      true(1)
                    }
                    MAX-ACCESS  read-only
                    STATUS  current -- was mandatory
                    DESCRIPTION
                    "Indicates whether the server blade specified exists or not."
                    ::= { bladeSysMgmtProcVPDEntry 3 }

        bladeSysMgmtProcVpdPowerState OBJECT-TYPE
                    SYNTAX  INTEGER {
                      off(0),
                      on(1),
                      standby(3),
                      hibernate(4)                      
                    }
                    MAX-ACCESS  read-only
                    STATUS  current -- was mandatory
                    DESCRIPTION
                    "Indicates the power state of the blade specified."
                    ::= { bladeSysMgmtProcVPDEntry 4 }

        bladeSysMgmtProcVpdName OBJECT-TYPE
                    SYNTAX  OCTET STRING
                    MAX-ACCESS  read-only
                    STATUS  current -- was mandatory
                    DESCRIPTION
                    "The name of the blade as a null terminated string."
                    ::= { bladeSysMgmtProcVPDEntry 5 }

        bladeSysMgmtProcVpdBuildId OBJECT-TYPE
                    SYNTAX  OCTET STRING
                    MAX-ACCESS  read-only
                    STATUS  current -- was mandatory
                    DESCRIPTION
                    "The build ID for the blade firmware."
                    ::= { bladeSysMgmtProcVPDEntry 6 }

        bladeSysMgmtProcVpdRevision OBJECT-TYPE
                    SYNTAX  OCTET STRING
                    MAX-ACCESS  read-only
                    STATUS  current -- was mandatory
                    DESCRIPTION
                    "The revision of the blade firmware."
                    ::= { bladeSysMgmtProcVPDEntry 7 }

       bladecKVMVPDTable OBJECT-TYPE
                      SYNTAX  SEQUENCE OF BladecKVMVPDEntry
                      MAX-ACCESS  not-accessible
                      STATUS  current -- was mandatory
                      DESCRIPTION
                      "Table of blade firmware vital product data (VPD) information."
                      ::= { bladeFirmwareVpd 4 }

        bladecKVMVPDEntry OBJECT-TYPE
                      SYNTAX BladecKVMVPDEntry
                      MAX-ACCESS  not-accessible
                      STATUS  current -- was mandatory
                      DESCRIPTION
                      "Blade firmware VPD table entry"
                      INDEX { bladecKVMVpdIndex }
                      ::= { bladecKVMVPDTable 1 }


        BladecKVMVPDEntry ::= SEQUENCE {
                    bladecKVMVpdIndex INTEGER,
                    bladecKVMVpdId INTEGER,
                    bladecKVMVpdExists INTEGER,
                    bladecKVMVpdPowerState INTEGER,
                    bladecKVMVpdName OCTET STRING,
                    bladecKVMVpdRevision OCTET STRING
                    }

        bladecKVMVpdIndex  OBJECT-TYPE
                    SYNTAX  Integer32 (0..2147483647) -- was INTEGER
                    MAX-ACCESS  read-only
                    STATUS  current -- was mandatory
                    DESCRIPTION
                    "Blade firmware VPD table index."
                    ::= { bladecKVMVPDEntry 1 }


        bladecKVMVpdId  OBJECT-TYPE
                    SYNTAX  INTEGER {
                      blade1(1),
                      blade2(2),
                      blade3(3),
                      blade4(4),
                      blade5(5),
                      blade6(6),
                      blade7(7),
                      blade8(8),
                      blade9(9),
                      blade10(10),
                      blade11(11),
                      blade12(12),
                      blade13(13),
                      blade14(14)
                    }
                    MAX-ACCESS  read-only
                    STATUS  current -- was mandatory
                    DESCRIPTION
                    "The numeric blade ID."
                    ::= { bladecKVMVPDEntry 2 }

        bladecKVMVpdExists OBJECT-TYPE
                    SYNTAX  INTEGER {
                      false(0),
                      true(1)
                    }
                    MAX-ACCESS  read-only
                    STATUS  current -- was mandatory
                    DESCRIPTION
                    "Indicates whether the blade specified exists or not."
                    ::= { bladecKVMVPDEntry 3 }

        bladecKVMVpdPowerState OBJECT-TYPE
                    SYNTAX  INTEGER {
                      off(0),
                      on(1),
                      standby(3),
                      hibernate(4)
                    }
                    MAX-ACCESS  read-only
                    STATUS  current -- was mandatory
                    DESCRIPTION
                   "Indicates the power state of the blade specified."
                    ::= { bladecKVMVPDEntry 4 }

        bladecKVMVpdName OBJECT-TYPE
                    SYNTAX  OCTET STRING
                    MAX-ACCESS  read-only
                    STATUS  current -- was mandatory
                    DESCRIPTION
                    "The name of the blade as a null terminated string."
                    ::= { bladecKVMVPDEntry 5 }

        bladecKVMVpdRevision OBJECT-TYPE
                    SYNTAX  OCTET STRING
                    MAX-ACCESS  read-only
                    STATUS  current -- was mandatory
                    DESCRIPTION
                    "The revision of the blade firmware."
                    ::= { bladecKVMVPDEntry 7 }

      -- ********************************************************************************
      -- Switch Module Hardware VPD
      -- ********************************************************************************
      smHardwareVpd OBJECT IDENTIFIER ::= { vpdInformation 6 }

      smHardwareVpdTable OBJECT-TYPE
                    SYNTAX  SEQUENCE OF SmHardwareVpdEntry
                    MAX-ACCESS  not-accessible
                    STATUS  current -- was mandatory
                    DESCRIPTION
                    "Table of the switch module hardware components.
                    For consistent results, view as a table and not as
                    individual entries."
                    ::= { smHardwareVpd 1 }

      smHardwareVpdEntry OBJECT-TYPE
                    SYNTAX SmHardwareVpdEntry
                    MAX-ACCESS  not-accessible
                    STATUS  current -- was mandatory
                    DESCRIPTION
                    "Switch module hardware VPD entry.
                    For consistent results, view as a table and
                    not as individual entries."
                    INDEX { smHardwareVpdIndex }
                    ::= { smHardwareVpdTable 1 }

      SmHardwareVpdEntry ::= SEQUENCE {
                  smHardwareVpdIndex INTEGER,
                  smHardwareVpdBayNumber OCTET STRING,
                  smHardwareVpdManufacturingId OCTET STRING,
                  smHardwareVpdFruNumber OCTET STRING,
                  smHardwareVpdHardwareRevision INTEGER,
                  smHardwareVpdUuid OCTET STRING,
                  smHardwareVpdManufDate OCTET STRING,
                  smHardwareVpdPartNumber OCTET STRING,
                  smHardwareVpdFruSerial OCTET STRING,
                  smHardwareVpdManufacturingIDNumber OCTET STRING,
                  smHardwareVpdProductId OCTET STRING,
                  smHardwareVpdSubManufacturerId OCTET STRING,
                  smHardwareVpdClei OCTET STRING,
                  smHardwareVpdWwnGuid OCTET STRING,
                  smHardwareVpdWwnGuidType OCTET STRING,
                  smHardwareVpdWidth INTEGER,
                  smHardwareVpdHardwareRevisionString OCTET STRING
                  }

      smHardwareVpdIndex  OBJECT-TYPE
                  SYNTAX  Integer32 (0..2147483647) -- was INTEGER
                  MAX-ACCESS  read-only
                  STATUS  current -- was mandatory
                  DESCRIPTION
                  "Switch module hardware VPD index.
                  For consistent results, view as a table and not as individual entries."
                  ::= { smHardwareVpdEntry 1 }

      smHardwareVpdBayNumber  OBJECT-TYPE
                  SYNTAX  OCTET STRING
                  MAX-ACCESS  read-only
                  STATUS  current -- was mandatory
                  DESCRIPTION
                  "Switch module hardware VPD Bay number.
                  For consistent results, view as a table and not as individual entries."
                  ::= { smHardwareVpdEntry 2 }

      smHardwareVpdManufacturingId  OBJECT-TYPE
                  SYNTAX  OCTET STRING
                  MAX-ACCESS  read-only
                  STATUS  current -- was mandatory
                  DESCRIPTION
                  "Switch module hardware VPD manufacturing ID.
                  For consistent results, view as a table and not as individual entries."
                  ::= { smHardwareVpdEntry 3 }

      smHardwareVpdFruNumber  OBJECT-TYPE
                  SYNTAX  OCTET STRING
                  MAX-ACCESS  read-only
                  STATUS  current -- was mandatory
                  DESCRIPTION
                  "Switch module hardware VPD FRU number.
                  For consistent results, view as a table and not as individual entries."
                  ::= { smHardwareVpdEntry 4 }


      smHardwareVpdHardwareRevision  OBJECT-TYPE
                  SYNTAX  INTEGER
                  MAX-ACCESS  read-only
                  STATUS  current -- was mandatory
                  DESCRIPTION
                  "Switch module hardware VPD hardware revision.
                  For consistent results, view as a table and not as individual entries.
                  If a hardware revision is programmed in the OEM VPD area for this component,
                  then the HardwareRevisionString version of this MIB object should be used."
                  ::= { smHardwareVpdEntry 5 }

      smHardwareVpdUuid  OBJECT-TYPE
                  SYNTAX  OCTET STRING
                  MAX-ACCESS  read-only
                  STATUS  current -- was mandatory
                  DESCRIPTION
                  "Switch module hardware VPD UUID.
                  For consistent results, view as a table and not as individual entries."
                  ::= { smHardwareVpdEntry 8 }

      smHardwareVpdManufDate  OBJECT-TYPE
                  SYNTAX  OCTET STRING
                  MAX-ACCESS  read-only
                  STATUS  current -- was mandatory
                  DESCRIPTION
                  "Switch module hardware VPD manufacture date.
                  For consistent results, view as a table and not as individual entries."
                  ::= { smHardwareVpdEntry 9 }

      smHardwareVpdPartNumber  OBJECT-TYPE
                  SYNTAX  OCTET STRING
                  MAX-ACCESS  read-only
                  STATUS  current -- was mandatory
                  DESCRIPTION
                  "Switch module hardware VPD Part Number.
                  For consistent results, view as a table and not as individual entries."
                  ::= { smHardwareVpdEntry 10 }

      smHardwareVpdFruSerial  OBJECT-TYPE
                  SYNTAX  OCTET STRING
                  MAX-ACCESS  read-only
                  STATUS  current -- was mandatory
                  DESCRIPTION
                  "Switch module hardware VPD FRU Serial.
                  For consistent results, view as a table and not as individual entries."
                  ::= { smHardwareVpdEntry 11 }

      smHardwareVpdManufacturingIDNumber  OBJECT-TYPE
                  SYNTAX  OCTET STRING
                  MAX-ACCESS  read-only
                  STATUS  current -- was mandatory
                  DESCRIPTION
                  "Switch module hardware VPD manufacturer ID.
                  For consistent results, view as a table and not as individual entries."
                  ::= { smHardwareVpdEntry 12 }

      smHardwareVpdProductId  OBJECT-TYPE
                  SYNTAX  OCTET STRING
                  MAX-ACCESS  read-only
                  STATUS  current -- was mandatory
                  DESCRIPTION
                  "Switch module hardware VPD product ID.
                  For consistent results, view as a table and not as individual entries."
                  ::= { smHardwareVpdEntry 13 }

      smHardwareVpdSubManufacturerId  OBJECT-TYPE
                  SYNTAX  OCTET STRING
                  MAX-ACCESS  read-only
                  STATUS  current -- was mandatory
                  DESCRIPTION
                  "Switch module hardware VPD subsystem manufacturer ID.
                  For consistent results, view as a table and not as individual entries."
                  ::= { smHardwareVpdEntry 14 }

      smHardwareVpdClei  OBJECT-TYPE
                  SYNTAX  OCTET STRING
                  MAX-ACCESS  read-only
                  STATUS  current -- was mandatory
                  DESCRIPTION
                  "Switch module hardware VPD Common Language Equipment Identifier (CLEI).
                  For consistent results, view as a table and not as individual entries."
                  ::= { smHardwareVpdEntry 15 }

      smHardwareVpdWwnGuid  OBJECT-TYPE
                  SYNTAX  OCTET STRING
                  MAX-ACCESS  read-only
                  STATUS  current -- was mandatory
                  DESCRIPTION
                  "Switch module hardware VPD World Wide Name or Global Unique ID.
                  For consistent results, view as a table and not as individual entries."
                  ::= { smHardwareVpdEntry 16 }

      smHardwareVpdWwnGuidType  OBJECT-TYPE
                  SYNTAX  OCTET STRING
                  MAX-ACCESS  read-only
                  STATUS  current -- was mandatory
                  DESCRIPTION
                  "The WWN/GUID/SAS entry is actually World Wide Name, Global Unique ID
                  or Serial Attach SCSI ID.
                  For consistent results, view as a table and not as individual entries."
                  ::= { smHardwareVpdEntry 17 }

      smHardwareVpdWidth OBJECT-TYPE
                  SYNTAX  INTEGER
                  MAX-ACCESS  read-only
                  STATUS  current -- was mandatory
                  DESCRIPTION
                  "The width of the switch module hardware.
                  For consistent results, view as a table and not as individual entries."
                  ::= { smHardwareVpdEntry 18 }

      smHardwareVpdHardwareRevisionString  OBJECT-TYPE
                  SYNTAX  OCTET STRING
                  MAX-ACCESS  read-only
                  STATUS  current -- was mandatory
                  DESCRIPTION
                  "Switch module hardware VPD hardware revision in string format.
                  For consistent results, view as a table and not as individual entries.
                  If a hardware revision is programmed in the OEM VPD area for this component,
                  then this MIB object should be used."
                  ::= { smHardwareVpdEntry 20 }

      -- ********************************************************************************
      -- Switch Interposer Hardware VPD
      -- ********************************************************************************

      smInpHardwareVpdTable OBJECT-TYPE
                  SYNTAX  SEQUENCE OF SmInpHardwareVpdEntry
                  MAX-ACCESS  not-accessible
                  STATUS  current -- was mandatory
                  DESCRIPTION
                  "Table of the switch interposer hardware components.
                  For consistent results, view as a table and not as individual entries.
                              
                  NOTE: This MIB object is for BladeCenter HS only." 
                  ::= { smHardwareVpd 2 }

      smInpHardwareVpdEntry OBJECT-TYPE
                  SYNTAX SmInpHardwareVpdEntry
                  MAX-ACCESS  not-accessible
                  STATUS  current -- was mandatory
                  DESCRIPTION
                  "Switch Interposer hardware VPD entry.
                  For consistent results, view as a table and not as individual entries.
                              
                  NOTE: This MIB object is for BladeCenter HS only." 
                  INDEX { smInpHardwareVpdIndex }
                  ::= { smInpHardwareVpdTable 1 }

      SmInpHardwareVpdEntry ::= SEQUENCE {
                  smInpHardwareVpdIndex INTEGER,
                  smInpHardwareVpdBayNumber OCTET STRING,
                  smInpHardwareVpdManufacturingId OCTET STRING,
                  smInpHardwareVpdFruNumber OCTET STRING,
                  smInpHardwareVpdHardwareRevision INTEGER,
                  smInpHardwareVpdUuid OCTET STRING,
                  smInpHardwareVpdManufDate OCTET STRING,
                  smInpHardwareVpdPartNumber OCTET STRING,
                  smInpHardwareVpdFruSerial OCTET STRING,
                  smInpHardwareVpdManufacturingIDNumber OCTET STRING,
                  smInpHardwareVpdProductId OCTET STRING,
                  smInpHardwareVpdSubManufacturerId OCTET STRING,
                  smInpHardwareVpdClei OCTET STRING,
                  smInpHardwareVpdWwnGuid OCTET STRING,
                  smInpHardwareVpdWwnGuidType OCTET STRING,
                  smInpHardwareVpdWidth INTEGER,
                  smInpHardwareVpdName OCTET STRING,
                  smInpHardwareVpdHardwareRevisionString OCTET STRING
                  }

      smInpHardwareVpdIndex  OBJECT-TYPE
                  SYNTAX  Integer32 (0..2147483647) -- was INTEGER
                  MAX-ACCESS  read-only
                  STATUS  current -- was mandatory
                  DESCRIPTION
                  "Switch Interposer hardware VPD index.
                  For consistent results, view as a table and not as individual entries.
                              
                  NOTE: This MIB object is for BladeCenter HS only." 
                  ::= { smInpHardwareVpdEntry 1 }

      smInpHardwareVpdBayNumber  OBJECT-TYPE
                  SYNTAX  OCTET STRING
                  MAX-ACCESS  read-only
                  STATUS  current -- was mandatory
                  DESCRIPTION
                  "Switch Interposer hardware VPD Bay number.
                  For consistent results, view as a table and not as individual entries.
                              
                  NOTE: This MIB object is for BladeCenter HS only." 
                  ::= { smInpHardwareVpdEntry 2 }
      
      smInpHardwareVpdManufacturingId  OBJECT-TYPE
                  SYNTAX  OCTET STRING
                  MAX-ACCESS  read-only
                  STATUS  current -- was mandatory
                  DESCRIPTION
                  "Switch Interposer hardware VPD manufacturing ID.
                  For consistent results, view as a table and not as individual entries.
                              
                  NOTE: This MIB object is for BladeCenter HS only." 
                  ::= { smInpHardwareVpdEntry 3 }

      smInpHardwareVpdFruNumber  OBJECT-TYPE
                  SYNTAX  OCTET STRING
                  MAX-ACCESS  read-only
                  STATUS  current -- was mandatory
                  DESCRIPTION
                  "Switch Interposer hardware VPD FRU number.
                  For consistent results, view as a table and not as individual entries.
                              
                  NOTE: This MIB object is for BladeCenter HS only." 
                  ::= { smInpHardwareVpdEntry 4 }


      smInpHardwareVpdHardwareRevision  OBJECT-TYPE
                  SYNTAX  INTEGER
                  MAX-ACCESS  read-only
                  STATUS  current -- was mandatory
                  DESCRIPTION
                  "Switch Interposer hardware VPD hardware revision.
                  For consistent results, view as a table and not as individual entries.
                              
                  NOTE: This MIB object is for BladeCenter HS only.
                   
                  If a hardware revision is programmed in the OEM VPD area for this component,
                  then the HardwareRevisionString version of this MIB object should be used."
                  ::= { smInpHardwareVpdEntry 5 }

      smInpHardwareVpdUuid  OBJECT-TYPE
                  SYNTAX  OCTET STRING
                  MAX-ACCESS  read-only
                  STATUS  current -- was mandatory
                  DESCRIPTION
                  "Switch Interposer hardware VPD UUID.
                  For consistent results, view as a table and not as individual entries.
                              
                  NOTE: This MIB object is for BladeCenter HS only." 
                  ::= { smInpHardwareVpdEntry 8 }

      smInpHardwareVpdManufDate  OBJECT-TYPE
                  SYNTAX  OCTET STRING
                  MAX-ACCESS  read-only
                  STATUS  current -- was mandatory
                  DESCRIPTION
                  "Switch Interposer hardware VPD manufacture Date.
                  For consistent results, view as a table and not as individual entries.
                              
                  NOTE: This MIB object is for BladeCenter HS only." 
                  ::= { smInpHardwareVpdEntry 9 }

      smInpHardwareVpdPartNumber  OBJECT-TYPE
                  SYNTAX  OCTET STRING
                  MAX-ACCESS  read-only
                  STATUS  current -- was mandatory
                  DESCRIPTION
                  "Switch Interposer hardware VPD Part Number.
                  For consistent results, view as a table and not as individual entries.
                              
                  NOTE: This MIB object is for BladeCenter HS only." 
                  ::= { smInpHardwareVpdEntry 10 }

      smInpHardwareVpdFruSerial  OBJECT-TYPE
                  SYNTAX  OCTET STRING
                  MAX-ACCESS  read-only
                  STATUS  current -- was mandatory
                  DESCRIPTION
                  "Switch Interposer module hardware VPD FRU Serial.
                  For consistent results, view as a table and not as individual entries.
                              
                  NOTE: This MIB object is for BladeCenter HS only." 
                  ::= { smInpHardwareVpdEntry 11 }     
                  
      smInpHardwareVpdManufacturingIDNumber  OBJECT-TYPE
                  SYNTAX  OCTET STRING
                  MAX-ACCESS  read-only
                  STATUS  current -- was mandatory
                  DESCRIPTION
                  "Switch Interposer module hardware VPD manufacturer ID Number.
                  For consistent results, view as a table and not as individual entries.
                              
                  NOTE: This MIB object is for BladeCenter HS only." 
                  ::= { smInpHardwareVpdEntry 12 }

      smInpHardwareVpdProductId  OBJECT-TYPE
                  SYNTAX  OCTET STRING
                  MAX-ACCESS  read-only
                  STATUS  current -- was mandatory
                  DESCRIPTION
                  "Switch Interposer module hardware VPD product ID.
                  For consistent results, view as a table and not as individual entries.
                              
                  NOTE: This MIB object is for BladeCenter HS only." 
                  ::= { smInpHardwareVpdEntry 13 }

      smInpHardwareVpdSubManufacturerId  OBJECT-TYPE
                  SYNTAX  OCTET STRING
                  MAX-ACCESS  read-only
                  STATUS  current -- was mandatory
                  DESCRIPTION
                  "Switch Interposer module hardware VPD subsystem manufacturer ID.
                  For consistent results, view as a table and not as individual entries.
                              
                  NOTE: This MIB object is for BladeCenter HS only." 
                  ::= { smInpHardwareVpdEntry 14 }

      smInpHardwareVpdClei  OBJECT-TYPE
                  SYNTAX  OCTET STRING
                  MAX-ACCESS  read-only
                  STATUS  current -- was mandatory
                  DESCRIPTION
                  "Switch Interposer module hardware VPD Common Language Equipment Identifier (CLEI).
                  For consistent results, view as a table and not as individual entries.
                              
                  NOTE: This MIB object is for BladeCenter HS only." 
                  ::= { smInpHardwareVpdEntry 15 }

      smInpHardwareVpdWwnGuid  OBJECT-TYPE
                  SYNTAX  OCTET STRING
                  MAX-ACCESS  read-only
                  STATUS  current -- was mandatory
                  DESCRIPTION
                  "Switch Interposer module hardware VPD World Wide Name or Global Unique ID.
                  For consistent results, view as a table and not as individual entries.
                              
                  NOTE: This MIB object is for BladeCenter HS only." 
                  ::= { smInpHardwareVpdEntry 16 }

      smInpHardwareVpdWwnGuidType  OBJECT-TYPE
                  SYNTAX  OCTET STRING
                  MAX-ACCESS  read-only
                  STATUS  current -- was mandatory
                  DESCRIPTION
                  "The Switch Interposer WWN/GUID/SAS entry is actually World Wide 
                  Name, Global Unique ID or Serial Attach SCSI ID.
                  For consistent results, view as a table and not as individual entries.
                              
                  NOTE: This MIB object is for BladeCenter HS only." 
                  ::= { smInpHardwareVpdEntry 17 }
      
      smInpHardwareVpdWidth OBJECT-TYPE
                  SYNTAX  INTEGER
                  MAX-ACCESS  read-only
                  STATUS  current -- was mandatory
                  DESCRIPTION
                  "The width of the switch Interposer module hardware.
                  For consistent results, view as a table and not as individual entries."
                  ::= { smInpHardwareVpdEntry 18 }

      smInpHardwareVpdName OBJECT-TYPE
                  SYNTAX  OCTET STRING
                  MAX-ACCESS  read-only
                  STATUS  current -- was mandatory
                  DESCRIPTION
                  "The Switch Interposer Name.
                  For consistent results, view as a table and not as individual entries.
                              
                  NOTE: This MIB object is for BladeCenter HS only." 
                  ::= { smInpHardwareVpdEntry 19 }            

      smInpHardwareVpdHardwareRevisionString  OBJECT-TYPE
                  SYNTAX  OCTET STRING
                  MAX-ACCESS  read-only
                  STATUS  current -- was mandatory
                  DESCRIPTION
                  "Switch Interposer hardware VPD hardware revision in string format.
                  For consistent results, view as a table and not as individual entries.
                              
                  NOTE: This MIB object is for BladeCenter HS only.
                   
                  If a hardware revision is programmed in the OEM VPD area for this component,
                  then this MIB object should be used."
                  ::= { smInpHardwareVpdEntry 20 }

       -- ********************************************************************************
       -- Switch module Information
       -- ********************************************************************************

       smFirmwareVpd OBJECT IDENTIFIER ::= { vpdInformation 7 }
        -- Server blade switch module information

         smMainAppVpdTable OBJECT-TYPE
                     SYNTAX  SEQUENCE OF SmMainAppVpdEntry
                     MAX-ACCESS  not-accessible
                     STATUS  current -- was mandatory
                     DESCRIPTION
                     "Switch module main application VPD information table."
                     ::= {smFirmwareVpd 1}

          smMainAppVpdEntry  OBJECT-TYPE
                        SYNTAX SmMainAppVpdEntry
                        MAX-ACCESS  not-accessible
                        STATUS  current -- was mandatory
                        DESCRIPTION
                        "Switch module main application VPD table entry"
                        INDEX { smMainAppVpdIndex }
                        ::= { smMainAppVpdTable 1 }

          SmMainAppVpdEntry ::= SEQUENCE {
                      smMainAppVpdIndex INTEGER,
                      smMainAppVpdId INTEGER,
                      smMainAppVpdExists INTEGER,
                      smMainAppVpdSwitchType INTEGER,
                      smMainApp1VpdBuildId OCTET STRING,
                      smMainApp1VpdBuildDate OCTET STRING,
                      smMainApp1VpdRevisionNumber OCTET STRING,
                      smMainApp2VpdBuildId OCTET STRING,
                      smMainApp2VpdBuildDate OCTET STRING,
                      smMainApp2VpdRevisionNumber OCTET STRING,
                      smMainApp3VpdBuildId OCTET STRING,
                      smMainApp3VpdBuildDate OCTET STRING,
                      smMainApp3VpdRevisionNumber OCTET STRING,
                      smMainAppVpdSwitchSubType INTEGER
                      }

          smMainAppVpdIndex OBJECT-TYPE
                      SYNTAX  Integer32 (0..2147483647) -- was INTEGER
                      MAX-ACCESS  read-only
                      STATUS  current -- was mandatory
                      DESCRIPTION
                      "Switch module main application VPD entry index."
                      ::= { smMainAppVpdEntry 1 }

          smMainAppVpdId OBJECT-TYPE
                      SYNTAX  INTEGER {
                        module1(1),
                        module2(2),
                        module3(3),
                        module4(4),
                        module5(5),
                        module6(6),
                        module7(7),
                        module8(8),
                        module9(9),
                        module10(10)
                      }
                      MAX-ACCESS  read-only
                      STATUS  current -- was mandatory
                      DESCRIPTION
                      "The switch module numeric identifier."
                      ::= { smMainAppVpdEntry 2 }

          smMainAppVpdExists OBJECT-TYPE
                      SYNTAX  INTEGER {
                        false(0),
                        true(1)
                      }
                      MAX-ACCESS  read-only
                      STATUS  current -- was mandatory
                      DESCRIPTION
                      "Indicates whether the switch module specified exists or not."
                      ::= { smMainAppVpdEntry 3 }

          smMainAppVpdSwitchType OBJECT-TYPE
                      SYNTAX  INTEGER {
                        unknown(0),
                        ethernet(1),
                        fibre(2),
                        opm(3),
                        serialCM(4),
                        copperPassThrough(5),
                        infiniband(6),
                        highSpeed(20),
                        passThrough(30),
                        sas(40)
                      }
                      MAX-ACCESS  read-only
                      STATUS  current -- was mandatory
                      DESCRIPTION
                      "Indicates the type of switch module installed."
                      ::= { smMainAppVpdEntry 4 }

          smMainApp1VpdBuildId OBJECT-TYPE
                        SYNTAX  OCTET STRING
                        MAX-ACCESS  read-only
                        STATUS  current -- was mandatory
                        DESCRIPTION
                        "Switch module firmware build id."
                        ::= { smMainAppVpdEntry 5 }

          smMainApp1VpdBuildDate OBJECT-TYPE
                        SYNTAX  OCTET STRING
                        MAX-ACCESS  read-only
                        STATUS  current -- was mandatory
                        DESCRIPTION
                        "Switch module firmware build date."
                        ::= { smMainAppVpdEntry 6 }

          smMainApp1VpdRevisionNumber OBJECT-TYPE
                        SYNTAX  OCTET STRING
                        MAX-ACCESS  read-only
                        STATUS  current -- was mandatory
                        DESCRIPTION
                        "Switch module firmware revision number."
                        ::= { smMainAppVpdEntry 7 }
          
          smMainApp2VpdBuildId OBJECT-TYPE
                        SYNTAX  OCTET STRING
                        MAX-ACCESS  read-only
                        STATUS  current -- was mandatory
                        DESCRIPTION
                        "Switch module firmware build id."
                        ::= { smMainAppVpdEntry 8 }

          smMainApp2VpdBuildDate OBJECT-TYPE
                        SYNTAX  OCTET STRING
                        MAX-ACCESS  read-only
                        STATUS  current -- was mandatory
                        DESCRIPTION
                        "Switch module firmware build date."
                        ::= { smMainAppVpdEntry 9 }

          smMainApp2VpdRevisionNumber OBJECT-TYPE
                        SYNTAX  OCTET STRING
                        MAX-ACCESS  read-only
                        STATUS  current -- was mandatory
                        DESCRIPTION
                        "Switch module firmware revision number."
                        ::= { smMainAppVpdEntry 10 }
          smMainApp3VpdBuildId OBJECT-TYPE
                        SYNTAX  OCTET STRING
                        MAX-ACCESS  read-only
                        STATUS  current -- was mandatory
                        DESCRIPTION
                        "I/O Module firmware build id."
                        ::= { smMainAppVpdEntry 11 }

          smMainApp3VpdBuildDate OBJECT-TYPE
                        SYNTAX  OCTET STRING
                        MAX-ACCESS  read-only
                        STATUS  current -- was mandatory
                        DESCRIPTION
                        "I/O Module firmware build date."
                        ::= { smMainAppVpdEntry 12 }

          smMainApp3VpdRevisionNumber OBJECT-TYPE
                        SYNTAX  OCTET STRING
                        MAX-ACCESS  read-only
                        STATUS  current -- was mandatory
                        DESCRIPTION
                        "I/O Module firmware revision number."
                        ::= { smMainAppVpdEntry 13 } 
                 
          smMainAppVpdSwitchSubType OBJECT-TYPE
                        SYNTAX  INTEGER {
                        unknown(0),
                        ethernet(1),
                        fibre(2),
                        infiniband(6),
                        sas(7),
                        raidsas(8),
                        icpm(9)
                      }
                      MAX-ACCESS  read-only
                      STATUS  current -- was mandatory
                      DESCRIPTION
                      "Indicates the subtype of switch module installed."
                      ::= { smMainAppVpdEntry 20 }



         smBootRomVpdTable OBJECT-TYPE
                     SYNTAX  SEQUENCE OF SmBootRomVpdEntry
                     MAX-ACCESS  not-accessible
                     STATUS  current -- was mandatory
                     DESCRIPTION
                     "Switch module boot ROM VPD information table."
                     ::= {smFirmwareVpd 2}

          smBootRomVpdEntry  OBJECT-TYPE
                        SYNTAX SmBootRomVpdEntry
                        MAX-ACCESS  not-accessible
                        STATUS  current -- was mandatory
                        DESCRIPTION
                        "Switch module boot ROM VPD table entry"
                        INDEX { smBootRomVpdIndex }
                        ::= { smBootRomVpdTable 1 }

          SmBootRomVpdEntry ::= SEQUENCE {
                      smBootRomVpdIndex INTEGER,
                      smBootRomVpdId INTEGER,
                      smBootRomVpdExists INTEGER,
                      smBootRomVpdSwitchType INTEGER,
                      smBootRomVpdBuildId OCTET STRING,
                      smBootRomVpdBuildDate OCTET STRING,
                      smBootRomVpdRevisionNumber OCTET STRING,
                      smBootRomVpdSwitchSubType INTEGER
                      }

          smBootRomVpdIndex OBJECT-TYPE
                      SYNTAX  Integer32 (0..2147483647) -- was INTEGER
                      MAX-ACCESS  read-only
                      STATUS  current -- was mandatory
                      DESCRIPTION
                      "Switch module boot ROM VPD entry index."
                      ::= { smBootRomVpdEntry 1 }

          smBootRomVpdId OBJECT-TYPE
                      SYNTAX  INTEGER {
                        module1(1),
                        module2(2),
                        module3(3),
                        module4(4),
                        module5(5),
                        module6(6),
                        module7(7),
                        module8(8),
                        module9(9),
                        module10(10)
                      }
                      MAX-ACCESS  read-only
                      STATUS  current -- was mandatory
                      DESCRIPTION
                      "The switch module numeric identifier."
                      ::= { smBootRomVpdEntry 2 }

          smBootRomVpdExists OBJECT-TYPE
                      SYNTAX  INTEGER {
                        false(0),
                        true(1)
                      }
                      MAX-ACCESS  read-only
                      STATUS  current -- was mandatory
                      DESCRIPTION
                      "Indicates whether the switch module specified exists or not."
                      ::= { smBootRomVpdEntry 3 }

          smBootRomVpdSwitchType OBJECT-TYPE
                      SYNTAX  INTEGER {
                        unknown(0),
                        ethernet(1),
                        fibre(2),
                        opm(3),
                        serialCM(4), 
                        copperPassThrough(5),
                        infiniband(6),
                        highSpeed(20),
                        passThrough(30),
                        sas(40)
                      }
                      MAX-ACCESS  read-only
                      STATUS  current -- was mandatory
                      DESCRIPTION
                      "Indicates the type of switch module installed."
                      ::= { smBootRomVpdEntry 4 }

          smBootRomVpdBuildId OBJECT-TYPE
                        SYNTAX  OCTET STRING
                        MAX-ACCESS  read-only
                        STATUS  current -- was mandatory
                        DESCRIPTION
                        "Switch module firmware build ID."
                        ::= { smBootRomVpdEntry 5 }

          smBootRomVpdBuildDate OBJECT-TYPE
                        SYNTAX  OCTET STRING
                        MAX-ACCESS  read-only
                        STATUS  current -- was mandatory
                        DESCRIPTION
                        "Switch module firmware build date."
                        ::= { smBootRomVpdEntry 6 }

          smBootRomVpdRevisionNumber OBJECT-TYPE
                        SYNTAX  OCTET STRING
                        MAX-ACCESS  read-only
                        STATUS  current -- was mandatory
                        DESCRIPTION
                        "Switch module firmware revision number."
                        ::= { smBootRomVpdEntry 7 }
          
          smBootRomVpdSwitchSubType OBJECT-TYPE
                      SYNTAX  INTEGER {
                        unknown(0),
                        ethernet(1),
                        fibre(2),
                        infiniband(6),
                        sas(7),
                        raidsas(8),
                        icpm(9)
                      }
                      MAX-ACCESS  read-only
                      STATUS  current -- was mandatory
                      DESCRIPTION
                      "Indicates the subtype of switch module installed."
                      ::= { smBootRomVpdEntry 8 }


      -- ********************************************************************************
      -- Power Module Hardware VPD
      -- ********************************************************************************
      pmHardwareVpd OBJECT IDENTIFIER ::= { vpdInformation 8 }

      pmHardwareVpdTable OBJECT-TYPE
                    SYNTAX  SEQUENCE OF PmHardwareVpdEntry
                    MAX-ACCESS  not-accessible
                    STATUS  current -- was mandatory
                    DESCRIPTION
                    "Table of the power module hardware components.
                    For consistent results, view as a table and not as individual entries."
                    ::= { pmHardwareVpd 1 }

      pmHardwareVpdEntry OBJECT-TYPE
                    SYNTAX PmHardwareVpdEntry
                    MAX-ACCESS  not-accessible
                    STATUS  current -- was mandatory
                    DESCRIPTION
                    "Power module hardware VPD entry.
                    For consistent results, view as a table and not as individual entries."
                    INDEX { pmHardwareVpdIndex }
                    ::= { pmHardwareVpdTable 1 }

      PmHardwareVpdEntry ::= SEQUENCE {
                  pmHardwareVpdIndex INTEGER,
                  pmHardwareVpdBayNumber OCTET STRING,
                  pmHardwareVpdManufacturingId OCTET STRING,
                  pmHardwareVpdFruNumber OCTET STRING,
                  pmHardwareVpdHardwareRevision INTEGER,
                  pmHardwareVpdUuid OCTET STRING,
                  pmHardwareVpdManufDate OCTET STRING,
                  pmHardwareVpdPartNumber OCTET STRING,
                  pmHardwareVpdFruSerial OCTET STRING,
                  pmHardwareVpdManufacturingIDNumber OCTET STRING,
                  pmHardwareVpdProductId OCTET STRING,
                  pmHardwareVpdSubManufacturerId OCTET STRING,
                  pmHardwareVpdClei OCTET STRING,
                  pmHardwareVpdHardwareRevisionString OCTET STRING
                  }

      pmHardwareVpdIndex  OBJECT-TYPE
                  SYNTAX  Integer32 (0..2147483647) -- was INTEGER
                  MAX-ACCESS  read-only
                  STATUS  current -- was mandatory
                  DESCRIPTION
                  "Power module hardware VPD index.
                  For consistent results, view as a table and not as individual entries."
                  ::= { pmHardwareVpdEntry 1 }

      pmHardwareVpdBayNumber  OBJECT-TYPE
                  SYNTAX  OCTET STRING
                  MAX-ACCESS  read-only
                  STATUS  current -- was mandatory
                  DESCRIPTION
                  "Power module hardware VPD Bay number.
                  For consistent results, view as a table and not as individual entries."
                  ::= { pmHardwareVpdEntry 2 }

      pmHardwareVpdManufacturingId  OBJECT-TYPE
                  SYNTAX  OCTET STRING
                  MAX-ACCESS  read-only
                  STATUS  current -- was mandatory
                  DESCRIPTION
                  "Power module hardware VPD manufacturing ID.
                  For consistent results, view as a table and not as individual entries."
                  ::= { pmHardwareVpdEntry 3 }

      pmHardwareVpdFruNumber  OBJECT-TYPE
                  SYNTAX  OCTET STRING
                  MAX-ACCESS  read-only
                  STATUS  current -- was mandatory
                  DESCRIPTION
                  "Power module hardware VPD FRU number.
                  For consistent results, view as a table and not as individual entries."
                  ::= { pmHardwareVpdEntry 4 }


      pmHardwareVpdHardwareRevision  OBJECT-TYPE
                  SYNTAX  INTEGER
                  MAX-ACCESS  read-only
                  STATUS  current -- was mandatory
                  DESCRIPTION
                  "Power module hardware VPD hardware revision.
                  For consistent results, view as a table and not as individual entries.
                  If a hardware revision is programmed in the OEM VPD area for this component,
                  then the HardwareRevisionString version of this MIB object should be used."
                  ::= { pmHardwareVpdEntry 5 }

      pmHardwareVpdUuid  OBJECT-TYPE
                  SYNTAX  OCTET STRING
                  MAX-ACCESS  read-only
                  STATUS  current -- was mandatory
                  DESCRIPTION
                  "Power module hardware VPD UUID.
                  For consistent results, view as a table and not as individual entries."
                  ::= { pmHardwareVpdEntry 8 }

      pmHardwareVpdManufDate  OBJECT-TYPE
                  SYNTAX  OCTET STRING
                  MAX-ACCESS  read-only
                  STATUS  current -- was mandatory
                  DESCRIPTION
                  "Power module hardware VPD Manufacture Date.
                  For consistent results, view as a table and not as individual entries."
                  ::= { pmHardwareVpdEntry 9 }

      pmHardwareVpdPartNumber  OBJECT-TYPE
                  SYNTAX  OCTET STRING
                  MAX-ACCESS  read-only
                  STATUS  current -- was mandatory
                  DESCRIPTION
                  "Power module hardware VPD Part Number.
                  For consistent results, view as a table and not as individual entries."
                  ::= { pmHardwareVpdEntry 10 }

      pmHardwareVpdFruSerial  OBJECT-TYPE
                  SYNTAX  OCTET STRING
                  MAX-ACCESS  read-only
                  STATUS  current -- was mandatory
                  DESCRIPTION
                  "Power module hardware VPD FRU Serial.
                  For consistent results, view as a table and not as individual entries."
                  ::= { pmHardwareVpdEntry 11 }

      pmHardwareVpdManufacturingIDNumber  OBJECT-TYPE
                  SYNTAX  OCTET STRING
                  MAX-ACCESS  read-only
                  STATUS  current -- was mandatory
                  DESCRIPTION
                  "Power module hardware VPD manufacturer ID.
                  For consistent results, view as a table and not as individual entries."
                  ::= { pmHardwareVpdEntry 12 }

      pmHardwareVpdProductId  OBJECT-TYPE
                  SYNTAX  OCTET STRING
                  MAX-ACCESS  read-only
                  STATUS  current -- was mandatory
                  DESCRIPTION
                  "Power module hardware VPD product ID.
                  For consistent results, view as a table and not as individual entries."
                  ::= { pmHardwareVpdEntry 13 }

      pmHardwareVpdSubManufacturerId  OBJECT-TYPE
                  SYNTAX  OCTET STRING
                  MAX-ACCESS  read-only
                  STATUS  current -- was mandatory
                  DESCRIPTION
                  "Power module hardware VPD subsystem manufacturer ID.
                  For consistent results, view as a table and not as individual entries."
                  ::= { pmHardwareVpdEntry 14 }

      pmHardwareVpdClei  OBJECT-TYPE
                  SYNTAX  OCTET STRING
                  MAX-ACCESS  read-only
                  STATUS  current -- was mandatory
                  DESCRIPTION
                  "Power module hardware VPD Common Language Equipment Identifier (CLEI).
                  For consistent results, view as a table and not as individual entries."
                  ::= { pmHardwareVpdEntry 15 }

      pmHardwareVpdHardwareRevisionString  OBJECT-TYPE
                  SYNTAX  OCTET STRING
                  MAX-ACCESS  read-only
                  STATUS  current -- was mandatory
                  DESCRIPTION
                  "Power module hardware VPD hardware revision in string format.
                  For consistent results, view as a table and not as individual entries.
                  If a hardware revision is programmed in the OEM VPD area for this component,
                  then this MIB object should be used."
                  ::= { pmHardwareVpdEntry 16 }
                  
      -- ********************************************************************************
      -- Media Tray Hardware VPD
      -- ********************************************************************************
      mtHardwareVpd OBJECT IDENTIFIER ::= { vpdInformation 9 }

      mtHardwareVpdManufacturingId  OBJECT-TYPE
                  SYNTAX  OCTET STRING
                  MAX-ACCESS  read-only
                  STATUS  current -- was mandatory
                  DESCRIPTION
                  "Media tray 1 hardware VPD manufacturing ID.
                  For consistent results, view as a table and not as individual entries."
                  ::= { mtHardwareVpd 3 }

      mtHardwareVpdFruNumber  OBJECT-TYPE
                  SYNTAX  OCTET STRING
                  MAX-ACCESS  read-only
                  STATUS  current -- was mandatory
                  DESCRIPTION
                  "Media tray 1 hardware VPD FRU number.
                  For consistent results, view as a table and not as individual entries."
                  ::= { mtHardwareVpd 4 }


      mtHardwareVpdHardwareRevision  OBJECT-TYPE
                  SYNTAX  INTEGER
                  MAX-ACCESS  read-only
                  STATUS  current -- was mandatory
                  DESCRIPTION
                  "Media tray 1 hardware VPD hardware revision.
                  For consistent results, view as a table and not as individual entries.
                  If a hardware revision is programmed in the OEM VPD area for this component,
                  then the HardwareRevisionString version of this MIB object should be used."
                  ::= { mtHardwareVpd 5 }

      mtHardwareVpdUuid  OBJECT-TYPE
                  SYNTAX  OCTET STRING
                  MAX-ACCESS  read-only
                  STATUS  current -- was mandatory
                  DESCRIPTION
                  "Media tray 1 hardware VPD UUID.
                  For consistent results, view as a table and not as individual entries."
                  ::= { mtHardwareVpd 8 }

      mtHardwareVpdManufacturingIDNumber  OBJECT-TYPE
                  SYNTAX  OCTET STRING
                  MAX-ACCESS  read-only
                  STATUS  current -- was mandatory
                  DESCRIPTION
                  "Media tray 1 hardware VPD manufacturer ID.
                  For consistent results, view as a table and not as individual entries."
                  ::= { mtHardwareVpd 9 }

      mtHardwareVpdProductId  OBJECT-TYPE
                  SYNTAX  OCTET STRING
                  MAX-ACCESS  read-only
                  STATUS  current -- was mandatory
                  DESCRIPTION
                  "Media tray 1 hardware VPD product ID.
                  For consistent results, view as a table and not as individual entries."
                  ::= { mtHardwareVpd 10 }

      mtHardwareVpdSubManufacturerId  OBJECT-TYPE
                  SYNTAX  OCTET STRING
                  MAX-ACCESS  read-only
                  STATUS  current -- was mandatory
                  DESCRIPTION
                  "Media tray 1 hardware VPD subsystem manufacturer ID.
                  For consistent results, view as a table and not as individual entries."
                  ::= { mtHardwareVpd 11 }

      mtHardwareVpdClei  OBJECT-TYPE
                  SYNTAX  OCTET STRING
                  MAX-ACCESS  read-only
                  STATUS  current -- was mandatory
                  DESCRIPTION
                  "Media tray 1 hardware VPD Common Language Equipment Identifier (CLEI).
                  For consistent results, view as a table and not as individual entries."
                  ::= { mtHardwareVpd 12 }
                  
      mtHardwareVpdCF1Capacity  OBJECT-TYPE
                  SYNTAX  OCTET STRING
                  MAX-ACCESS  read-only
                  STATUS  current -- was mandatory
                  DESCRIPTION
                  "Media tray 1 hardware VPD CompactFlash card capacity.
                  For consistent results, view as a table and not as individual entries."
                  ::= { mtHardwareVpd 13 }
                  
      mtHardwareVpdCF2Capacity  OBJECT-TYPE
                  SYNTAX  OCTET STRING
                  MAX-ACCESS  read-only
                  STATUS  current -- was mandatory
                  DESCRIPTION
                  "Media tray 1 hardware VPD CompactFlash card capacity.
                  For consistent results, view as a table and not as individual entries."
                  ::= { mtHardwareVpd 14 }            

      mtHardwareVpdBBU1 OBJECT-TYPE
                   SYNTAX INTEGER {
                     no(0),
                     yes(1)
                   }
                   MAX-ACCESS  read-only
                   STATUS  current -- was mandatory
                   DESCRIPTION
                   "Indicates the presence of Battery Backup Unit 1.
                   
                   NOTE: This MIB object is for BCS only."
                   ::= { mtHardwareVpd 15 }

      mtHardwareVpdBBU2 OBJECT-TYPE
                   SYNTAX INTEGER {
                     no(0),
                     yes(1)
                   }
                   MAX-ACCESS  read-only
                   STATUS  current -- was mandatory
                   DESCRIPTION
                   "Indicates the presence of Battery Backup Unit 2.
                   
                   NOTE: This MIB object is for BCS only."
                   ::= { mtHardwareVpd 16 }
                   
      mtHardwareVpdHardwareRevisionString  OBJECT-TYPE
                  SYNTAX  OCTET STRING
                  MAX-ACCESS  read-only
                  STATUS  current -- was mandatory
                  DESCRIPTION
                  "Media tray 1 hardware VPD hardware revision in string format.
                  For consistent results, view as a table and not as individual entries.
                  If a hardware revision is programmed in the OEM VPD area for this component,
                  then this  MIB object should be used."
                  ::= { mtHardwareVpd 17 }

      -- ********************************************************************************
      -- Bottom Media Tray Hardware VPD
      -- ********************************************************************************
      mt2HardwareVpd OBJECT IDENTIFIER ::= { vpdInformation 10 }

      mt2HardwareVpdManufacturingId  OBJECT-TYPE
                  SYNTAX  OCTET STRING
                  MAX-ACCESS  read-only
                  STATUS  current -- was mandatory
                  DESCRIPTION
                  "Media tray 2 hardware VPD manufacturing ID.
                  For consistent results, view as a table and not as individual entries."
                  ::= { mt2HardwareVpd 3 }

      mt2HardwareVpdFruNumber  OBJECT-TYPE
                  SYNTAX  OCTET STRING
                  MAX-ACCESS  read-only
                  STATUS  current -- was mandatory
                  DESCRIPTION
                  "Media tray 2 hardware VPD FRU number.
                  For consistent results, view as a table and not as individual entries."
                  ::= { mt2HardwareVpd 4 }


      mt2HardwareVpdHardwareRevision  OBJECT-TYPE
                  SYNTAX  INTEGER
                  MAX-ACCESS  read-only
                  STATUS  current -- was mandatory
                  DESCRIPTION
                  "Media tray 2 hardware VPD hardware revision.
                  For consistent results, view as a table and not as individual entries.
                  If a hardware revision is programmed in the OEM VPD area for this component,
                  then the HardwareRevisionString version of this MIB object should be used."
                  ::= { mt2HardwareVpd 5 }

      mt2HardwareVpdUuid  OBJECT-TYPE
                  SYNTAX  OCTET STRING
                  MAX-ACCESS  read-only
                  STATUS  current -- was mandatory
                  DESCRIPTION
                  "Media tray 2 hardware VPD UUID.
                  For consistent results, view as a table and not as individual entries."
                  ::= { mt2HardwareVpd 8 }

      mt2HardwareVpdManufacturingIDNumber  OBJECT-TYPE
                  SYNTAX  OCTET STRING
                  MAX-ACCESS  read-only
                  STATUS  current -- was mandatory
                  DESCRIPTION
                  "Media tray 2 hardware VPD manufacturer ID.
                  For consistent results, view as a table and not as individual entries."
                  ::= { mt2HardwareVpd 9 }

      mt2HardwareVpdProductId  OBJECT-TYPE
                  SYNTAX  OCTET STRING
                  MAX-ACCESS  read-only
                  STATUS  current -- was mandatory
                  DESCRIPTION
                  "Media tray 2 hardware VPD product ID.
                  For consistent results, view as a table and not as individual entries."
                  ::= { mt2HardwareVpd 10 }

      mt2HardwareVpdSubManufacturerId  OBJECT-TYPE
                  SYNTAX  OCTET STRING
                  MAX-ACCESS  read-only
                  STATUS  current -- was mandatory
                  DESCRIPTION
                  "Media tray 2 hardware VPD subsystem manufacturer ID.
                  For consistent results, view as a table and not as individual entries."
                  ::= { mt2HardwareVpd 11 }

      mt2HardwareVpdClei  OBJECT-TYPE
                  SYNTAX  OCTET STRING
                  MAX-ACCESS  read-only
                  STATUS  current -- was mandatory
                  DESCRIPTION
                  "Media tray 2 hardware VPD Common Language Equipment Identifier (CLEI).
                  For consistent results, view as a table and not as individual entries."
                  ::= { mt2HardwareVpd 12 }
      
      mt2HardwareVpdCF1Capacity  OBJECT-TYPE
                  SYNTAX  OCTET STRING
                  MAX-ACCESS  read-only
                  STATUS  current -- was mandatory
                  DESCRIPTION
                  "Media tray 2 hardware VPD CompactFlash card capacity.
                  For consistent results, view as a table and not as individual entries."
                  ::= { mt2HardwareVpd 13 }
                  
      mt2HardwareVpdCF2Capacity  OBJECT-TYPE
                  SYNTAX  OCTET STRING
                  MAX-ACCESS  read-only
                  STATUS  current -- was mandatory
                  DESCRIPTION
                  "Media tray 2 hardware VPD CompactFlash card capacity.
                  For consistent results, view as a table and not as individual entries."
                  ::= { mt2HardwareVpd 14 }
                    
      mt2HardwareVpdHardwareRevisionString  OBJECT-TYPE
                  SYNTAX  OCTET STRING
                  MAX-ACCESS  read-only
                  STATUS  current -- was mandatory
                  DESCRIPTION
                  "Media tray 2 hardware VPD hardware revision in string format.
                  For consistent results, view as a table and not as individual entries.
                  If a hardware revision is programmed in the OEM VPD area for this component,
                  then this  MIB object should be used."
                  ::= { mt2HardwareVpd 17 }

      -- ********************************************************************************
      -- Blower Firmware Level VPD
      -- ********************************************************************************
      blowerFirmwareVpd OBJECT IDENTIFIER ::= { vpdInformation 12 }

       blowerControllerVPDTable OBJECT-TYPE
                      SYNTAX  SEQUENCE OF BlowerControllerVPDEntry
                      MAX-ACCESS  not-accessible
                      STATUS  current -- was mandatory
                      DESCRIPTION
                      "Table of blower controller firmware vital product data (VPD) information.

                      NOTE: Blowers are also referred to as Chassis Cooling Devices."
                      ::= { blowerFirmwareVpd 1 }

        blowerControllerVPDEntry OBJECT-TYPE
                      SYNTAX BlowerControllerVPDEntry
                      MAX-ACCESS  not-accessible
                      STATUS  current -- was mandatory
                      DESCRIPTION
                      "Blower controller firmware VPD table entry"
                      INDEX { blowerControllerVpdIndex }
                      ::= { blowerControllerVPDTable 1 }


        BlowerControllerVPDEntry ::= SEQUENCE {
                    blowerControllerVpdIndex INTEGER,
                    blowerControllerVpdId INTEGER,
                    blowerControllerVpdExists INTEGER,
                    blowerControllerVpdRevision OCTET STRING
                    }

        blowerControllerVpdIndex  OBJECT-TYPE
                    SYNTAX  Integer32 (0..2147483647) -- was INTEGER
                    MAX-ACCESS  read-only
                    STATUS  current -- was mandatory
                    DESCRIPTION
                    "Blower controller firmware VPD table index."
                    ::= { blowerControllerVPDEntry 1 }


        blowerControllerVpdId  OBJECT-TYPE
                    SYNTAX  INTEGER {
                      blower1(1),
                      blower2(2),
                      blower3(3),
                      blower4(4)
                    }
                    MAX-ACCESS  read-only
                    STATUS  current -- was mandatory
                    DESCRIPTION
                    "The numeric blower ID."
                    ::= { blowerControllerVPDEntry 2 }

        blowerControllerVpdExists OBJECT-TYPE
                    SYNTAX  INTEGER {
                      false(0),
                      true(1)
                    }
                    MAX-ACCESS  read-only
                    STATUS  current -- was mandatory
                    DESCRIPTION
                    "Indicates whether the blower specified exists or not."
                    ::= { blowerControllerVPDEntry 3 }

        blowerControllerVpdRevision OBJECT-TYPE
                    SYNTAX  OCTET STRING
                    MAX-ACCESS  read-only
                    STATUS  current -- was mandatory
                    DESCRIPTION
                    "The revision of the blower controller firmware."
                    ::= { blowerControllerVPDEntry 7 }


      -- ********************************************************************************
      -- Blower Hardware VPD
      -- ********************************************************************************
      blowerHardwareVpd OBJECT IDENTIFIER ::= { vpdInformation 13 }

      blowerHardwareVpdTable OBJECT-TYPE
                    SYNTAX  SEQUENCE OF BlowerHardwareVpdEntry
                    MAX-ACCESS  not-accessible
                    STATUS  current -- was mandatory
                    DESCRIPTION
                    "Table of the blower hardware components.
                    For consistent results, view as a table and not as individual entries.

                    NOTE: Blowers are also referred to as Chassis Cooling Devices."
                    ::= { blowerHardwareVpd 1 }

      blowerHardwareVpdEntry OBJECT-TYPE
                    SYNTAX BlowerHardwareVpdEntry
                    MAX-ACCESS  not-accessible
                    STATUS  current -- was mandatory
                    DESCRIPTION
                    "Blower hardware VPD entry.
                    For consistent results, view as a table and not as individual entries."
                    INDEX { blowerHardwareVpdIndex }
                    ::= { blowerHardwareVpdTable 1 }

      BlowerHardwareVpdEntry ::= SEQUENCE {
                  blowerHardwareVpdIndex INTEGER,
                  blowerHardwareVpdBayNumber OCTET STRING,
                  blowerHardwareVpdManufacturingId OCTET STRING,
                  blowerHardwareVpdFruNumber OCTET STRING,
                  blowerHardwareVpdHardwareRevision INTEGER,
                  blowerHardwareVpdUuid OCTET STRING,
                  blowerHardwareVpdManufDate OCTET STRING,
                  blowerHardwareVpdPartNumber OCTET STRING,
                  blowerHardwareVpdFruSerial OCTET STRING,
                  blowerHardwareVpdManufacturingIDNumber OCTET STRING,
                  blowerHardwareVpdProductId OCTET STRING,
                  blowerHardwareVpdSubManufacturerId OCTET STRING,
                  blowerHardwareVpdClei OCTET STRING,
                  blowerHardwareVpdHardwareRevisionString OCTET STRING
                  }

      blowerHardwareVpdIndex  OBJECT-TYPE
                  SYNTAX  Integer32 (0..2147483647) -- was INTEGER
                  MAX-ACCESS  read-only
                  STATUS  current -- was mandatory
                  DESCRIPTION
                  "Blower hardware VPD index.
                  For consistent results, view as a table and not as individual entries."
                  ::= { blowerHardwareVpdEntry 1 }

      blowerHardwareVpdBayNumber  OBJECT-TYPE
                  SYNTAX  OCTET STRING
                  MAX-ACCESS  read-only
                  STATUS  current -- was mandatory
                  DESCRIPTION
                  "Blower hardware VPD Bay number.
                  For consistent results, view as a table and not as individual entries."
                  ::= { blowerHardwareVpdEntry 2 }

      blowerHardwareVpdManufacturingId  OBJECT-TYPE
                  SYNTAX  OCTET STRING
                  MAX-ACCESS  read-only
                  STATUS  current -- was mandatory
                  DESCRIPTION
                  "Blower hardware VPD manufacturing ID.
                  For consistent results, view as a table and not as individual entries."
                  ::= { blowerHardwareVpdEntry 3 }

      blowerHardwareVpdFruNumber  OBJECT-TYPE
                  SYNTAX  OCTET STRING
                  MAX-ACCESS  read-only
                  STATUS  current -- was mandatory
                  DESCRIPTION
                  "Blower hardware VPD FRU number.
                  For consistent results, view as a table and not as individual entries."
                  ::= { blowerHardwareVpdEntry 4 }


      blowerHardwareVpdHardwareRevision  OBJECT-TYPE
                  SYNTAX  INTEGER
                  MAX-ACCESS  read-only
                  STATUS  current -- was mandatory
                  DESCRIPTION
                  "Blower hardware VPD hardware revision.
                  For consistent results, view as a table and not as individual entries.
                  If a hardware revision is programmed in the OEM VPD area for this component,
                  then the HardwareRevisionString version of this MIB object should be used."
                  ::= { blowerHardwareVpdEntry 5 }

      blowerHardwareVpdUuid  OBJECT-TYPE
                  SYNTAX  OCTET STRING
                  MAX-ACCESS  read-only
                  STATUS  current -- was mandatory
                  DESCRIPTION
                  "Blower hardware VPD UUID.
                  For consistent results, view as a table and not as individual entries."
                  ::= { blowerHardwareVpdEntry 8 }

      blowerHardwareVpdManufDate  OBJECT-TYPE
                  SYNTAX  OCTET STRING
                  MAX-ACCESS  read-only
                  STATUS  current -- was mandatory
                  DESCRIPTION
                  "Blower hardware VPD manufacture Date.
                  For consistent results, view as a table and not as individual entries."
                  ::= { blowerHardwareVpdEntry 9 }

      blowerHardwareVpdPartNumber  OBJECT-TYPE
                  SYNTAX  OCTET STRING
                  MAX-ACCESS  read-only
                  STATUS  current -- was mandatory
                  DESCRIPTION
                  "Blower hardware VPD Part Number.
                  For consistent results, view as a table and not as individual entries."
                  ::= { blowerHardwareVpdEntry 10 }

      blowerHardwareVpdFruSerial  OBJECT-TYPE
                  SYNTAX  OCTET STRING
                  MAX-ACCESS  read-only
                  STATUS  current -- was mandatory
                  DESCRIPTION
                  "Blower hardware VPD FRU serial number.
                  For consistent results, view as a table and not as individual entries."
                  ::= { blowerHardwareVpdEntry 11 }

      blowerHardwareVpdManufacturingIDNumber  OBJECT-TYPE
                  SYNTAX  OCTET STRING
                  MAX-ACCESS  read-only
                  STATUS  current -- was mandatory
                  DESCRIPTION
                  "Blower hardware VPD manufacturer ID.
                  For consistent results, view as a table and not as individual entries."
                  ::= { blowerHardwareVpdEntry 12 }

      blowerHardwareVpdProductId  OBJECT-TYPE
                  SYNTAX  OCTET STRING
                  MAX-ACCESS  read-only
                  STATUS  current -- was mandatory
                  DESCRIPTION
                  "Blower hardware VPD product ID.
                  For consistent results, view as a table and not as individual entries."
                  ::= { blowerHardwareVpdEntry 13 }

      blowerHardwareVpdSubManufacturerId  OBJECT-TYPE
                  SYNTAX  OCTET STRING
                  MAX-ACCESS  read-only
                  STATUS  current -- was mandatory
                  DESCRIPTION
                  "Blower hardware VPD subsystem manufacturer ID.
                  For consistent results, view as a table and not as individual entries."
                  ::= { blowerHardwareVpdEntry 14 }

      blowerHardwareVpdClei  OBJECT-TYPE
                  SYNTAX  OCTET STRING
                  MAX-ACCESS  read-only
                  STATUS  current -- was mandatory
                  DESCRIPTION
                  "Blower hardware VPD Common Language Equipment Identifier (CLEI).
                  For consistent results, view as a table and not as individual entries."
                  ::= { blowerHardwareVpdEntry 15 }

      blowerHardwareVpdHardwareRevisionString  OBJECT-TYPE
                  SYNTAX  OCTET STRING
                  MAX-ACCESS  read-only
                  STATUS  current -- was mandatory
                  DESCRIPTION
                  "Blower hardware VPD hardware revision in string format.
                  For consistent results, view as a table and not as individual entries.
                  If a hardware revision is programmed in the OEM VPD area for this component,
                  then this MIB object should be used."
                  ::= { blowerHardwareVpdEntry 16 }
                  
      -- ********************************************************************************
      -- Fan Pack Firmware Level VPD
      -- ********************************************************************************
      fanPackFirmwareVpd OBJECT IDENTIFIER ::= { vpdInformation 14 }

       fanPackControllerVPDTable OBJECT-TYPE
                      SYNTAX  SEQUENCE OF FanPackControllerVPDEntry
                      MAX-ACCESS  not-accessible
                      STATUS  current -- was mandatory
                      DESCRIPTION
                      "Table of fan pack controller firmware vital product data (VPD) information.

                      NOTE: Fan packs are also referred to as Power Module Chassis Cooling Devices."
                      ::= { fanPackFirmwareVpd 1 }

        fanPackControllerVPDEntry OBJECT-TYPE
                      SYNTAX FanPackControllerVPDEntry
                      MAX-ACCESS  not-accessible
                      STATUS  current -- was mandatory
                      DESCRIPTION
                      "Fan Pack controller firmware VPD table entry"
                      INDEX { fanPackControllerVpdIndex }
                      ::= { fanPackControllerVPDTable 1 }

        FanPackControllerVPDEntry ::= SEQUENCE {
                    fanPackControllerVpdIndex INTEGER,
                    fanPackControllerVpdId INTEGER,
                    fanPackControllerVpdExists INTEGER,
                    fanPackControllerVpdRevision OCTET STRING
                    }

        fanPackControllerVpdIndex  OBJECT-TYPE
                    SYNTAX  Integer32 (0..2147483647) -- was INTEGER
                    MAX-ACCESS  read-only
                    STATUS  current -- was mandatory
                    DESCRIPTION
                    "Fan Pack controller firmware VPD table index."
                    ::= { fanPackControllerVPDEntry 1 }

        fanPackControllerVpdId  OBJECT-TYPE
                    SYNTAX  INTEGER {
                      fanPack1(1),
                      fanPack2(2),
                      fanPack3(3),
                      fanPack4(4)
                    }
                    MAX-ACCESS  read-only
                    STATUS  current -- was mandatory
                    DESCRIPTION
                    "The numeric fan pack ID."
                    ::= { fanPackControllerVPDEntry 2 }

        fanPackControllerVpdExists OBJECT-TYPE
                    SYNTAX  INTEGER {
                      false(0),
                      true(1)
                    }
                    MAX-ACCESS  read-only
                    STATUS  current -- was mandatory
                    DESCRIPTION
                    "Indicates whether the fan pack specified exists or not."
                    ::= { fanPackControllerVPDEntry 3 }

        fanPackControllerVpdRevision OBJECT-TYPE
                    SYNTAX  OCTET STRING
                    MAX-ACCESS  read-only
                    STATUS  current -- was mandatory
                    DESCRIPTION
                    "The revision of the fan pack controller firmware."
                    ::= { fanPackControllerVPDEntry 7 }



      -- ********************************************************************************
      -- Telco Alarm Panel Hardware VPD
      -- ********************************************************************************
      tapHardwareVpd OBJECT IDENTIFIER ::= { vpdInformation 15 }

      tapHardwareVpdManufacturingId  OBJECT-TYPE
                  SYNTAX  OCTET STRING
                  MAX-ACCESS  read-only
                  STATUS  current -- was mandatory
                  DESCRIPTION
                  "Telco Alarm Panel hardware VPD manufacturing ID.
                  For consistent results, view as a table and not as individual entries.
                              
                  NOTE: This MIB object is for BladeCenter HT only." 
                  ::= { tapHardwareVpd 3 }

      tapHardwareVpdFruNumber  OBJECT-TYPE
                  SYNTAX  OCTET STRING
                  MAX-ACCESS  read-only
                  STATUS  current -- was mandatory
                  DESCRIPTION
                  "Telco Alarm Panel hardware VPD FRU number.
                  For consistent results, view as a table and not as individual entries.
                              
                  NOTE: This MIB object is for BladeCenter HT only." 
                  ::= { tapHardwareVpd 4 }


      tapHardwareVpdHardwareRevision  OBJECT-TYPE
                  SYNTAX  INTEGER
                  MAX-ACCESS  read-only
                  STATUS  current -- was mandatory
                  DESCRIPTION
                  "Telco Alarm Panel hardware VPD hardware revision.
                  For consistent results, view as a table and not as individual entries.
                              
                  NOTE: This MIB object is for BladeCenter HT only.
                   
                  If a hardware revision is programmed in the OEM VPD area for this component,
                  then the HardwareRevisionString version of this MIB object should be used."
                  ::= { tapHardwareVpd 5 }

      tapHardwareVpdUuid  OBJECT-TYPE
                  SYNTAX  OCTET STRING
                  MAX-ACCESS  read-only
                  STATUS  current -- was mandatory
                  DESCRIPTION
                  "Telco Alarm Panel hardware VPD UUID.
                  For consistent results, view as a table and not as individual entries.
                              
                  NOTE: This MIB object is for BladeCenter HT only." 
                  ::= { tapHardwareVpd 8 }

      tapHardwareVpdManufDate  OBJECT-TYPE
                  SYNTAX  OCTET STRING
                  MAX-ACCESS  read-only
                  STATUS  current -- was mandatory
                  DESCRIPTION
                  "Telco Alarm Panel hardware VPD manufacture Date.
                  For consistent results, view as a table and not as individual entries.
                              
                  NOTE: This MIB object is for BladeCenter HT only." 
                  ::= { tapHardwareVpd 9 }

      tapHardwareVpdPartNumber  OBJECT-TYPE
                  SYNTAX  OCTET STRING
                  MAX-ACCESS  read-only
                  STATUS  current -- was mandatory
                  DESCRIPTION
                  "Telco Alarm Panel hardware VPD Part Number.
                  For consistent results, view as a table and not as individual entries.
                              
                  NOTE: This MIB object is for BladeCenter HT only." 
                  ::= { tapHardwareVpd 10 }

      tapHardwareVpdFruSerial  OBJECT-TYPE
                  SYNTAX  OCTET STRING
                  MAX-ACCESS  read-only
                  STATUS  current -- was mandatory
                  DESCRIPTION
                  "Telco Alarm Panel hardware VPD FRU Serial.
                  For consistent results, view as a table and not as individual entries.
                              
                  NOTE: This MIB object is for BladeCenter HT only." 
                  ::= { tapHardwareVpd 11 }
                  
      tapHardwareVpdManufacturingIDNumber  OBJECT-TYPE
                  SYNTAX  OCTET STRING
                  MAX-ACCESS  read-only
                  STATUS  current -- was mandatory
                  DESCRIPTION
                  "Telco Alarm Panel hardware VPD manufacturer ID.
                  For consistent results, view as a table and not as individual entries."
                  ::= { tapHardwareVpd 12 }

      tapHardwareVpdProductId  OBJECT-TYPE
                  SYNTAX  OCTET STRING
                  MAX-ACCESS  read-only
                  STATUS  current -- was mandatory
                  DESCRIPTION
                  "Telco Alarm Panel hardware VPD product ID.
                  For consistent results, view as a table and not as individual entries."
                  ::= { tapHardwareVpd 13 }

      tapHardwareVpdSubManufacturerId  OBJECT-TYPE
                  SYNTAX  OCTET STRING
                  MAX-ACCESS  read-only
                  STATUS  current -- was mandatory
                  DESCRIPTION
                  "Telco Alarm Panel hardware VPD subsystem manufacturer ID.
                  For consistent results, view as a table and not as individual entries."
                  ::= { tapHardwareVpd 14 }

      tapHardwareVpdClei  OBJECT-TYPE
                  SYNTAX  OCTET STRING
                  MAX-ACCESS  read-only
                  STATUS  current -- was mandatory
                  DESCRIPTION
                  "Telco Alarm Panel hardware VPD Common Language Equipment Identifier (CLEI).
                  For consistent results, view as a table and not as individual entries."
                  ::= { tapHardwareVpd 15 }
      
      tapHardwareVpdHardwareRevisionString  OBJECT-TYPE
                  SYNTAX  OCTET STRING
                  MAX-ACCESS  read-only
                  STATUS  current -- was mandatory
                  DESCRIPTION
                  "Telco Alarm Panel hardware VPD hardware revision in string format.
                  For consistent results, view as a table and not as individual entries.
                              
                  NOTE: This MIB object is for BladeCenter HT only.
                   
                  If a hardware revision is programmed in the OEM VPD area for this component,
                  then this MIB object should be used."
                  ::= { tapHardwareVpd 16 }
                  
      -- ********************************************************************************
      -- Network Clock Hardware VPD
      -- ********************************************************************************
      ncHardwareVpd OBJECT IDENTIFIER ::= { vpdInformation 16 }
      
        ncHardwareVpdTable OBJECT-TYPE
                  SYNTAX  SEQUENCE OF NcHardwareVpdEntry
                  MAX-ACCESS  not-accessible
                  STATUS  current -- was mandatory
                  DESCRIPTION
                  "Table of the Network Clock hardware components.
                  For consistent results, view as a table and not as individual entries.
                              
                  NOTE: This MIB object is for BladeCenter HT only." 
                  ::= { ncHardwareVpd 1 }

        ncHardwareVpdEntry OBJECT-TYPE
                  SYNTAX NcHardwareVpdEntry
                  MAX-ACCESS  not-accessible
                  STATUS  current -- was mandatory
                  DESCRIPTION
                  "Network Clock hardware VPD entry.
                  For consistent results, view as a table and not as individual entries.
                              
                  NOTE: This MIB object is for BladeCenter HT only." 
                  INDEX { ncHardwareVpdIndex }
                  ::= { ncHardwareVpdTable 1 }

        NcHardwareVpdEntry ::= SEQUENCE {
                  ncHardwareVpdIndex INTEGER,
                  ncHardwareVpdBayNumber OCTET STRING,
                  ncHardwareVpdManufacturingId OCTET STRING,
                  ncHardwareVpdFruNumber OCTET STRING,
                  ncHardwareVpdHardwareRevision INTEGER,
                  ncHardwareVpdUuid OCTET STRING,
                  ncHardwareVpdManufDate OCTET STRING,
                  ncHardwareVpdPartNumber OCTET STRING,
                  ncHardwareVpdFruSerial OCTET STRING,
                  ncHardwareVpdManufacturingIDNumber OCTET STRING,
                  ncHardwareVpdProductId OCTET STRING,
                  ncHardwareVpdSubManufacturerId OCTET STRING,
                  ncHardwareVpdClei OCTET STRING,
                  ncHardwareVpdHardwareRevisionString OCTET STRING
                  }

        ncHardwareVpdIndex  OBJECT-TYPE
                  SYNTAX  Integer32 (0..2147483647) -- was INTEGER
                  MAX-ACCESS  read-only
                  STATUS  current -- was mandatory
                  DESCRIPTION
                  "Network Clock hardware VPD index.
                  For consistent results, view as a table and not as individual entries.
                              
                  NOTE: This MIB object is for BladeCenter HT only." 
                  ::= { ncHardwareVpdEntry 1 }

        ncHardwareVpdBayNumber  OBJECT-TYPE
                  SYNTAX  OCTET STRING
                  MAX-ACCESS  read-only
                  STATUS  current -- was mandatory
                  DESCRIPTION
                  "Network Clock hardware VPD Bay number.
                  For consistent results, view as a table and not as individual entries.
                              
                  NOTE: This MIB object is for BladeCenter HT only." 
                  ::= { ncHardwareVpdEntry 2 }

        ncHardwareVpdManufacturingId  OBJECT-TYPE
                  SYNTAX  OCTET STRING
                  MAX-ACCESS  read-only
                  STATUS  current -- was mandatory
                  DESCRIPTION
                  "Network Clock hardware VPD manufacturing ID.
                  For consistent results, view as a table and not as individual entries.
                              
                  NOTE: This MIB object is for BladeCenter HT only." 
                  ::= { ncHardwareVpdEntry 3 }

        ncHardwareVpdFruNumber  OBJECT-TYPE
                  SYNTAX  OCTET STRING
                  MAX-ACCESS  read-only
                  STATUS  current -- was mandatory
                  DESCRIPTION
                  "Network Clock hardware VPD FRU number.
                  For consistent results, view as a table and not as individual entries.
                              
                  NOTE: This MIB object is for BladeCenter HT only." 
                  ::= { ncHardwareVpdEntry 4 }


        ncHardwareVpdHardwareRevision  OBJECT-TYPE
                  SYNTAX  INTEGER
                  MAX-ACCESS  read-only
                  STATUS  current -- was mandatory
                  DESCRIPTION
                  "Network Clock hardware VPD hardware revision.
                  For consistent results, view as a table and not as individual entries.
                              
                  NOTE: This MIB object is for BladeCenter HT only.
                   
                  If a hardware revision is programmed in the OEM VPD area for this component,
                  then the HardwareRevisionString version of this MIB object should be used."
                  ::= { ncHardwareVpdEntry 5 }

        ncHardwareVpdUuid  OBJECT-TYPE
                  SYNTAX  OCTET STRING
                  MAX-ACCESS  read-only
                  STATUS  current -- was mandatory
                  DESCRIPTION
                  "Network Clock hardware VPD UUID.
                  For consistent results, view as a table and not as individual entries.
                              
                  NOTE: This MIB object is for BladeCenter HT only." 
                  ::= { ncHardwareVpdEntry 8 }

        ncHardwareVpdManufDate  OBJECT-TYPE
                  SYNTAX  OCTET STRING
                  MAX-ACCESS  read-only
                  STATUS  current -- was mandatory
                  DESCRIPTION
                  "Network Clock hardware VPD manufacture Date.
                  For consistent results, view as a table and not as individual entries.
                              
                  NOTE: This MIB object is for BladeCenter HT only." 
                  ::= { ncHardwareVpdEntry 9 }

        ncHardwareVpdPartNumber  OBJECT-TYPE
                  SYNTAX  OCTET STRING
                  MAX-ACCESS  read-only
                  STATUS  current -- was mandatory
                  DESCRIPTION
                  "Network Clock hardware VPD Part Number.
                  For consistent results, view as a table and not as individual entries.
                              
                  NOTE: This MIB object is for BladeCenter HT only." 
                  ::= { ncHardwareVpdEntry 10 }

        ncHardwareVpdFruSerial  OBJECT-TYPE
                  SYNTAX  OCTET STRING
                  MAX-ACCESS  read-only
                  STATUS  current -- was mandatory
                  DESCRIPTION
                  "Network Clock hardware VPD FRU serial number.
                  For consistent results, view as a table and not as individual entries.
                              
                  NOTE: This MIB object is for BladeCenter HT only." 
                  ::= { ncHardwareVpdEntry 11 } 
                  
        ncHardwareVpdManufacturingIDNumber  OBJECT-TYPE
                  SYNTAX  OCTET STRING
                  MAX-ACCESS  read-only
                  STATUS  current -- was mandatory
                  DESCRIPTION
                  "Network Clock hardware VPD manufacturer ID.
                  For consistent results, view as a table and not as individual entries."
                  ::= { ncHardwareVpdEntry 12 }

        ncHardwareVpdProductId  OBJECT-TYPE
                  SYNTAX  OCTET STRING
                  MAX-ACCESS  read-only
                  STATUS  current -- was mandatory
                  DESCRIPTION
                  "Network Clock hardware VPD product ID.
                  For consistent results, view as a table and not as individual entries."
                  ::= { ncHardwareVpdEntry 13 }

        ncHardwareVpdSubManufacturerId  OBJECT-TYPE
                  SYNTAX  OCTET STRING
                  MAX-ACCESS  read-only
                  STATUS  current -- was mandatory
                  DESCRIPTION
                  "Network Clock hardware VPD subsystem manufacturer ID.
                  For consistent results, view as a table and not as individual entries."
                  ::= { ncHardwareVpdEntry 14 }

        ncHardwareVpdClei  OBJECT-TYPE
                  SYNTAX  OCTET STRING
                  MAX-ACCESS  read-only
                  STATUS  current -- was mandatory
                  DESCRIPTION
                  "Network Clock hardware VPD Common Language Equipment Identifier (CLEI).
                  For consistent results, view as a table and not as individual entries."
                  ::= { ncHardwareVpdEntry 15 }          
       
        ncHardwareVpdHardwareRevisionString  OBJECT-TYPE
                  SYNTAX  OCTET STRING
                  MAX-ACCESS  read-only
                  STATUS  current -- was mandatory
                  DESCRIPTION
                  "Network Clock hardware VPD hardware revision in string format.
                  For consistent results, view as a table and not as individual entries.
                              
                  NOTE: This MIB object is for BladeCenter HT only.
                   
                  If a hardware revision is programmed in the OEM VPD area for this component,
                  then this MIB object should be used."
                  ::= { ncHardwareVpdEntry 16 }
                  
      -- ********************************************************************************
      -- Multiplexer Expansion Module Hardware VPD
      -- ********************************************************************************
      mxHardwareVpd OBJECT IDENTIFIER ::= { vpdInformation 17 }
      
        mxHardwareVpdTable OBJECT-TYPE
                  SYNTAX  SEQUENCE OF MxHardwareVpdEntry
                  MAX-ACCESS  not-accessible
                  STATUS  current -- was mandatory
                  DESCRIPTION
                  "Table of the Multiplexer Expansion Module hardware components.
                  For consistent results, view as a table and not as individual entries.
                              
                  NOTE: This MIB object is for BladeCenter HT only." 
                  ::= { mxHardwareVpd 1 }

        mxHardwareVpdEntry OBJECT-TYPE
                  SYNTAX MxHardwareVpdEntry
                  MAX-ACCESS  not-accessible
                  STATUS  current -- was mandatory
                  DESCRIPTION
                  "Multiplexer Expansion Module hardware VPD entry.
                  For consistent results, view as a table and not as individual entries.
                              
                  NOTE: This MIB object is for BladeCenter HT only." 
                  INDEX { mxHardwareVpdIndex }
                  ::= { mxHardwareVpdTable 1 }

        MxHardwareVpdEntry ::= SEQUENCE {
                  mxHardwareVpdIndex INTEGER,
                  mxHardwareVpdBayNumber OCTET STRING,
                  mxHardwareVpdManufacturingId OCTET STRING,
                  mxHardwareVpdFruNumber OCTET STRING,
                  mxHardwareVpdHardwareRevision INTEGER,
                  mxHardwareVpdUuid OCTET STRING,
                  mxHardwareVpdManufDate OCTET STRING,
                  mxHardwareVpdPartNumber OCTET STRING,
                  mxHardwareVpdFruSerial OCTET STRING,
                  mxHardwareVpdManufacturingIDNumber OCTET STRING,
                  mxHardwareVpdProductId OCTET STRING,
                  mxHardwareVpdSubManufacturerId OCTET STRING,
                  mxHardwareVpdClei OCTET STRING,
                  mxHardwareVpdHardwareRevisionString OCTET STRING
                  }

        mxHardwareVpdIndex  OBJECT-TYPE
                  SYNTAX  Integer32 (0..2147483647) -- was INTEGER
                  MAX-ACCESS  read-only
                  STATUS  current -- was mandatory
                  DESCRIPTION
                  "Multiplexer Expansion Module hardware VPD index.
                  For consistent results, view as a table and not as individual entries.
                              
                  NOTE: This MIB object is for BladeCenter HT only." 
                  ::= { mxHardwareVpdEntry 1 }

        mxHardwareVpdBayNumber  OBJECT-TYPE
                  SYNTAX  OCTET STRING
                  MAX-ACCESS  read-only
                  STATUS  current -- was mandatory
                  DESCRIPTION
                  "Multiplexer Expansion Module hardware VPD Bay number.
                  For consistent results, view as a table and not as individual entries.
                              
                  NOTE: This MIB object is for BladeCenter HT only." 
                  ::= { mxHardwareVpdEntry 2 }

        mxHardwareVpdManufacturingId  OBJECT-TYPE
                  SYNTAX  OCTET STRING
                  MAX-ACCESS  read-only
                  STATUS  current -- was mandatory
                  DESCRIPTION
                  "Multiplexer Expansion Module hardware VPD manufacturing ID.
                  For consistent results, view as a table and not as individual entries.
                              
                  NOTE: This MIB object is for BladeCenter HT only." 
                  ::= { mxHardwareVpdEntry 3 }

        mxHardwareVpdFruNumber  OBJECT-TYPE
                  SYNTAX  OCTET STRING
                  MAX-ACCESS  read-only
                  STATUS  current -- was mandatory
                  DESCRIPTION
                  "Multiplexer Expansion Module hardware VPD FRU number.
                  For consistent results, view as a table and not as individual entries.
                              
                  NOTE: This MIB object is for BladeCenter HT only." 
                  ::= { mxHardwareVpdEntry 4 }


        mxHardwareVpdHardwareRevision  OBJECT-TYPE
                  SYNTAX  INTEGER
                  MAX-ACCESS  read-only
                  STATUS  current -- was mandatory
                  DESCRIPTION
                  "Multiplexer Expansion Module hardware VPD hardware revision.
                  For consistent results, view as a table and not as individual entries.
                              
                  NOTE: This MIB object is for BladeCenter HT only.
                   
                  If a hardware revision is programmed in the OEM VPD area for this component,
                  then the HardwareRevisionString version of this MIB object should be used."
                  ::= { mxHardwareVpdEntry 5 }

        mxHardwareVpdUuid  OBJECT-TYPE
                  SYNTAX  OCTET STRING
                  MAX-ACCESS  read-only
                  STATUS  current -- was mandatory
                  DESCRIPTION
                  "Multiplexer Expansion Module hardware VPD UUID.
                  For consistent results, view as a table and not as individual entries.
                              
                  NOTE: This MIB object is for BladeCenter HT only." 
                  ::= { mxHardwareVpdEntry 8 }

        mxHardwareVpdManufDate  OBJECT-TYPE
                  SYNTAX  OCTET STRING
                  MAX-ACCESS  read-only
                  STATUS  current -- was mandatory
                  DESCRIPTION
                  "Multiplexer Expansion Module hardware VPD manufacture Date.
                  For consistent results, view as a table and not as individual entries.
                              
                  NOTE: This MIB object is for BladeCenter HT only." 
                  ::= { mxHardwareVpdEntry 9 }

        mxHardwareVpdPartNumber  OBJECT-TYPE
                  SYNTAX  OCTET STRING
                  MAX-ACCESS  read-only
                  STATUS  current -- was mandatory
                  DESCRIPTION
                  "Multiplexer Expansion Module hardware VPD Part Number.
                  For consistent results, view as a table and not as individual entries.
                              
                  NOTE: This MIB object is for BladeCenter HT only." 
                  ::= { mxHardwareVpdEntry 10 }

        mxHardwareVpdFruSerial  OBJECT-TYPE
                  SYNTAX  OCTET STRING
                  MAX-ACCESS  read-only
                  STATUS  current -- was mandatory
                  DESCRIPTION
                  "Multiplexer Expansion Module hardware VPD FRU Serial Number.
                  For consistent results, view as a table and not as individual entries.
                              
                  NOTE: This MIB object is for BladeCenter HT only." 
                  ::= { mxHardwareVpdEntry 11 }
         
        mxHardwareVpdManufacturingIDNumber  OBJECT-TYPE
                  SYNTAX  OCTET STRING
                  MAX-ACCESS  read-only
                  STATUS  current -- was mandatory
                  DESCRIPTION
                  "Multiplexer Expansion Module hardware VPD manufacturer ID.
                  For consistent results, view as a table and not as individual entries."
                  ::= { mxHardwareVpdEntry 12 }

        mxHardwareVpdProductId  OBJECT-TYPE
                  SYNTAX  OCTET STRING
                  MAX-ACCESS  read-only
                  STATUS  current -- was mandatory
                  DESCRIPTION
                  "Multiplexer Expansion Module hardware VPD product ID.
                  For consistent results, view as a table and not as individual entries."
                  ::= { mxHardwareVpdEntry 13 }

        mxHardwareVpdSubManufacturerId  OBJECT-TYPE
                  SYNTAX  OCTET STRING
                  MAX-ACCESS  read-only
                  STATUS  current -- was mandatory
                  DESCRIPTION
                  "Multiplexer Expansion Module hardware VPD subsystem manufacturer ID.
                  For consistent results, view as a table and not as individual entries."
                  ::= { mxHardwareVpdEntry 14 }

        mxHardwareVpdClei  OBJECT-TYPE
                  SYNTAX  OCTET STRING
                  MAX-ACCESS  read-only
                  STATUS  current -- was mandatory
                  DESCRIPTION
                  "Multiplexer Expansion Module hardware VPD Common 
                  Language Equipment Identifier (CLEI).
                  For consistent results, view as a table and not as individual entries."
                  ::= { mxHardwareVpdEntry 15 }  

        mxHardwareVpdHardwareRevisionString  OBJECT-TYPE
                  SYNTAX  OCTET STRING
                  MAX-ACCESS  read-only
                  STATUS  current -- was mandatory
                  DESCRIPTION
                  "Multiplexer Expansion Module hardware VPD hardware revision in string format.
                  For consistent results, view as a table and not as individual entries.
                              
                  NOTE: This MIB object is for BladeCenter HT only.
                   
                  If a hardware revision is programmed in the OEM VPD area for this component,
                  then this MIB object should be used."
                  ::= { mxHardwareVpdEntry 16 }

      -- ********************************************************************************
      -- Storage Module Hardware VPD
      -- ********************************************************************************
      stmHardwareVpd OBJECT IDENTIFIER ::= { vpdInformation 18 }
      
        stmHardwareVpdTable OBJECT-TYPE
                  SYNTAX  SEQUENCE OF StmHardwareVpdEntry
                  MAX-ACCESS  not-accessible
                  STATUS  current -- was mandatory
                  DESCRIPTION
                  "Table of the Storage Module hardware components.
                  For consistent results, view as a table and not as individual entries.
                              
                  NOTE: This MIB object is for BCS only." 
                  ::= { stmHardwareVpd 1 }

        stmHardwareVpdEntry OBJECT-TYPE
                  SYNTAX  StmHardwareVpdEntry
                  MAX-ACCESS  not-accessible
                  STATUS  current -- was mandatory
                  DESCRIPTION
                  "Storage Module hardware VPD entry.
                  For consistent results, view as a table and not as individual entries.
                              
                  NOTE: This MIB object is for BCS only." 
                  INDEX { stmHardwareVpdIndex }
                  ::= { stmHardwareVpdTable 1 }

        StmHardwareVpdEntry ::= SEQUENCE {
                  stmHardwareVpdIndex INTEGER,
                  stmHardwareVpdBayNumber OCTET STRING,
                  stmHardwareVpdManufacturingId OCTET STRING,
                  stmHardwareVpdFruNumber OCTET STRING,
                  stmHardwareVpdHardwareRevision INTEGER,
                  stmHardwareVpdUuid OCTET STRING,
                  stmHardwareVpdManufDate OCTET STRING,
                  stmHardwareVpdPartNumber OCTET STRING,
                  stmHardwareVpdFruSerial OCTET STRING,
                  stmHardwareVpdManufacturingIDNumber OCTET STRING,
                  stmHardwareVpdProductId OCTET STRING,
                  stmHardwareVpdSubManufacturerId OCTET STRING,
                  stmHardwareVpdClei OCTET STRING,
                  stmHardwareVpdHardwareRevisionString OCTET STRING
                  }

        stmHardwareVpdIndex  OBJECT-TYPE
                  SYNTAX  Integer32 (0..2147483647) -- was INTEGER
                  MAX-ACCESS  read-only
                  STATUS  current -- was mandatory
                  DESCRIPTION
                  "Storage Module hardware VPD index.
                  For consistent results, view as a table and not as individual entries.
                              
                  NOTE: This MIB object is for BCS only." 
                  ::= { stmHardwareVpdEntry 1 }

        stmHardwareVpdBayNumber  OBJECT-TYPE
                  SYNTAX  OCTET STRING
                  MAX-ACCESS  read-only
                  STATUS  current -- was mandatory
                  DESCRIPTION
                  "Storage Module hardware VPD Bay number.
                  For consistent results, view as a table and not as individual entries.
                              
                  NOTE: This MIB object is for BCS only." 
                  ::= { stmHardwareVpdEntry 2 }

        stmHardwareVpdManufacturingId  OBJECT-TYPE
                  SYNTAX  OCTET STRING
                  MAX-ACCESS  read-only
                  STATUS  current -- was mandatory
                  DESCRIPTION
                  "Storage Module hardware VPD manufacturing ID.
                  For consistent results, view as a table and not as individual entries.
                              
                  NOTE: This MIB object is for BCS only." 
                  ::= { stmHardwareVpdEntry 3 }

        stmHardwareVpdFruNumber  OBJECT-TYPE
                  SYNTAX  OCTET STRING
                  MAX-ACCESS  read-only
                  STATUS  current -- was mandatory
                  DESCRIPTION
                  "Storage Module hardware VPD FRU number.
                  For consistent results, view as a table and not as individual entries.
                              
                  NOTE: This MIB object is for BCS only." 
                  ::= { stmHardwareVpdEntry 4 }


        stmHardwareVpdHardwareRevision  OBJECT-TYPE
                  SYNTAX  INTEGER
                  MAX-ACCESS  read-only
                  STATUS  current -- was mandatory
                  DESCRIPTION
                  "Storage Module hardware VPD hardware revision.
                  For consistent results, view as a table and not as individual entries.
                              
                  NOTE: This MIB object is for BCS only.
                   
                  If a hardware revision is programmed in the OEM VPD area for this component,
                  then the HardwareRevisionString version of this MIB object should be used."
                  ::= { stmHardwareVpdEntry 5 }

        stmHardwareVpdUuid  OBJECT-TYPE
                  SYNTAX  OCTET STRING
                  MAX-ACCESS  read-only
                  STATUS  current -- was mandatory
                  DESCRIPTION
                  "Storage Module hardware VPD UUID.
                  For consistent results, view as a table and not as individual entries.
                              
                  NOTE: This MIB object is for BCS only." 
                  ::= { stmHardwareVpdEntry 8 }

        stmHardwareVpdManufDate  OBJECT-TYPE
                  SYNTAX  OCTET STRING
                  MAX-ACCESS  read-only
                  STATUS  current -- was mandatory
                  DESCRIPTION
                  "Storage Module hardware VPD manufacture Date.
                  For consistent results, view as a table and not as individual entries.
                              
                  NOTE: This MIB object is for BCS only." 
                  ::= { stmHardwareVpdEntry 9 }

        stmHardwareVpdPartNumber  OBJECT-TYPE
                  SYNTAX  OCTET STRING
                  MAX-ACCESS  read-only
                  STATUS  current -- was mandatory
                  DESCRIPTION
                  "Storage Module hardware VPD Part Number.
                  For consistent results, view as a table and not as individual entries.
                              
                  NOTE: This MIB object is for BCS only." 
                  ::= { stmHardwareVpdEntry 10 }

        stmHardwareVpdFruSerial  OBJECT-TYPE
                  SYNTAX  OCTET STRING
                  MAX-ACCESS  read-only
                  STATUS  current -- was mandatory
                  DESCRIPTION
                  "Storage Module hardware VPD FRU Serial Number.
                  For consistent results, view as a table and not as individual entries.
                              
                  NOTE: This MIB object is for BCS only." 
                  ::= { stmHardwareVpdEntry 11 }
         
        stmHardwareVpdManufacturingIDNumber  OBJECT-TYPE
                  SYNTAX  OCTET STRING
                  MAX-ACCESS  read-only
                  STATUS  current -- was mandatory
                  DESCRIPTION
                  "Storage Module hardware VPD manufacturer ID.
                  For consistent results, view as a table and not as individual entries."
                  ::= { stmHardwareVpdEntry 12 }

        stmHardwareVpdProductId  OBJECT-TYPE
                  SYNTAX  OCTET STRING
                  MAX-ACCESS  read-only
                  STATUS  current -- was mandatory
                  DESCRIPTION
                  "Storage Module hardware VPD product ID.
                  For consistent results, view as a table and not as individual entries."
                  ::= { stmHardwareVpdEntry 13 }

        stmHardwareVpdSubManufacturerId  OBJECT-TYPE
                  SYNTAX  OCTET STRING
                  MAX-ACCESS  read-only
                  STATUS  current -- was mandatory
                  DESCRIPTION
                  "Storage Module hardware VPD subsystem manufacturer ID.
                  For consistent results, view as a table and not as individual entries."
                  ::= { stmHardwareVpdEntry 14 }

        stmHardwareVpdClei  OBJECT-TYPE
                  SYNTAX  OCTET STRING
                  MAX-ACCESS  read-only
                  STATUS  current -- was mandatory
                  DESCRIPTION
                  "Storage Module hardware VPD Common 
                  Language Equipment Identifier (CLEI).
                  For consistent results, view as a table and not as individual entries."
                  ::= { stmHardwareVpdEntry 15 }  
                  
        stmHardwareVpdHardwareRevisionString  OBJECT-TYPE
                  SYNTAX  OCTET STRING
                  MAX-ACCESS  read-only
                  STATUS  current -- was mandatory
                  DESCRIPTION
                  "Storage Module hardware VPD hardware revision in string format.
                  For consistent results, view as a table and not as individual entries.
                              
                  NOTE: This MIB object is for BCS only.
                   
                  If a hardware revision is programmed in the OEM VPD area for this component,
                  then this MIB object should be used."
                  ::= { stmHardwareVpdEntry 16 }

      -- ***********************************************************************
      -- Storage Module Firmware VPD
      -- ***********************************************************************
      stmFirmwareVpd OBJECT IDENTIFIER ::= { vpdInformation 19 }

        stmFirmwareVpdTable OBJECT-TYPE
                  SYNTAX  SEQUENCE OF StmFirmwareVpdEntry
                  MAX-ACCESS  not-accessible
                  STATUS  current -- was mandatory
                  DESCRIPTION
                  "Table of the Storage Module firmware components.
                  For consistent results, view as a table and not as individual entries.

                  NOTE: This MIB object is for BCS only."
                  ::= { stmFirmwareVpd 1 }

        stmFirmwareVpdEntry OBJECT-TYPE
                  SYNTAX  StmFirmwareVpdEntry
                  MAX-ACCESS  not-accessible
                  STATUS  current -- was mandatory
                  DESCRIPTION
                  "Storage Module firmware VPD entry.
                  For consistent results, view as a table and not as individual entries.

                  NOTE: This MIB object is for BCS only."
                  INDEX { stmFirmwareVpdIndex }
                  ::= { stmFirmwareVpdTable 1 }

        StmFirmwareVpdEntry ::= SEQUENCE {
                  stmFirmwareVpdIndex INTEGER,
                  stmFirmwareVpdType OCTET STRING,
                  stmFirmwareVpdBuildId OCTET STRING,
                  stmFirmwareVpdReleaseDate OCTET STRING,
                  stmFirmwareVpdRevision OCTET STRING
                  }

        stmFirmwareVpdIndex  OBJECT-TYPE
                  SYNTAX  Integer32 (0..2147483647) -- was INTEGER
                  MAX-ACCESS  read-only
                  STATUS  current -- was mandatory
                  DESCRIPTION
                  "Storage Module firmware VPD index.
                  For consistent results, view as a table and not as individual entries.

                  NOTE: This MIB object is for BCS only."
                  ::= { stmFirmwareVpdEntry 1 }

        stmFirmwareVpdType  OBJECT-TYPE
                  SYNTAX  OCTET STRING
                  MAX-ACCESS  read-only
                  STATUS  current -- was mandatory
                  DESCRIPTION
                  "Storage Module firmware VPD type.
                  For consistent results, view as a table and not as individual entries.

                  NOTE: This MIB object is for BCS only."
                  ::= { stmFirmwareVpdEntry 2 }

        stmFirmwareVpdBuildId  OBJECT-TYPE
                  SYNTAX  OCTET STRING
                  MAX-ACCESS  read-only
                  STATUS  current -- was mandatory
                  DESCRIPTION
                  "Storage Module firmware VPD build ID.
                  For consistent results, view as a table and not as individual entries.

                  NOTE: This MIB object is for BCS only."
                  ::= { stmFirmwareVpdEntry 3 }

        stmFirmwareVpdReleaseDate  OBJECT-TYPE
                  SYNTAX  OCTET STRING
                  MAX-ACCESS  read-only
                  STATUS  current -- was mandatory
                  DESCRIPTION
                  "Storage Module firmware VPD release date.
                  For consistent results, view as a table and not as individual entries.

                  NOTE: This MIB object is for BCS only."
                  ::= { stmFirmwareVpdEntry 4 }

        stmFirmwareVpdRevision  OBJECT-TYPE
                  SYNTAX  OCTET STRING
                  MAX-ACCESS  read-only
                  STATUS  current -- was mandatory
                  DESCRIPTION
                  "Storage Module firmware VPD revision.
                  For consistent results, view as a table and not as individual entries.

                  NOTE: This MIB object is for BCS only."
                  ::= { stmFirmwareVpdEntry 5 }

      -- ********************************************************************************
      -- Battery Backup Unit Hardware VPD
      -- ********************************************************************************
      bbuHardwareVpd OBJECT IDENTIFIER ::= { vpdInformation 21 }
      
        bbuHardwareVpdTable OBJECT-TYPE
                  SYNTAX  SEQUENCE OF BbuHardwareVpdEntry
                  MAX-ACCESS  not-accessible
                  STATUS  current -- was mandatory
                  DESCRIPTION
                  "Table of the Battery Backup Unit hardware components.
                  For consistent results, view as a table and not as individual entries.
                              
                  NOTE: This MIB object is for BCS only." 
                  ::= { bbuHardwareVpd 1 }

        bbuHardwareVpdEntry OBJECT-TYPE
                  SYNTAX  BbuHardwareVpdEntry
                  MAX-ACCESS  not-accessible
                  STATUS  current -- was mandatory
                  DESCRIPTION
                  "Battery Backup Unit hardware VPD entry.
                  For consistent results, view as a table and not as individual entries.
                              
                  NOTE: This MIB object is for BCS only." 
                  INDEX { bbuHardwareVpdIndex }
                  ::= { bbuHardwareVpdTable 1 }

        BbuHardwareVpdEntry ::= SEQUENCE {
                  bbuHardwareVpdIndex INTEGER,
                  bbuHardwareVpdBayNumber OCTET STRING,
                  bbuHardwareVpdManufacturingId OCTET STRING,
                  bbuHardwareVpdFruNumber OCTET STRING,
                  bbuHardwareVpdHardwareRevision INTEGER,
                  bbuHardwareVpdUuid OCTET STRING,
                  bbuHardwareVpdManufDate OCTET STRING,
                  bbuHardwareVpdPartNumber OCTET STRING,
                  bbuHardwareVpdFruSerial OCTET STRING,
                  bbuHardwareVpdManufacturingIDNumber OCTET STRING,
                  bbuHardwareVpdProductId OCTET STRING,
                  bbuHardwareVpdSubManufacturerId OCTET STRING,
                  bbuHardwareVpdClei OCTET STRING
                  }

        bbuHardwareVpdIndex  OBJECT-TYPE
                  SYNTAX  Integer32 (0..2147483647) -- was INTEGER
                  MAX-ACCESS  read-only
                  STATUS  current -- was mandatory
                  DESCRIPTION
                  "Battery Backup Unit hardware VPD index.
                  For consistent results, view as a table and not as individual entries.
                              
                  NOTE: This MIB object is for BCS only."
                  ::= { bbuHardwareVpdEntry 1 }

        bbuHardwareVpdBayNumber  OBJECT-TYPE
                  SYNTAX  OCTET STRING
                  MAX-ACCESS  read-only
                  STATUS  current -- was mandatory
                  DESCRIPTION
                  "Battery Backup Unit hardware VPD Bay number.
                  For consistent results, view as a table and not as individual entries.
                              
                  NOTE: This MIB object is for BCS only."
                  ::= { bbuHardwareVpdEntry 2 }

        bbuHardwareVpdManufacturingId  OBJECT-TYPE
                  SYNTAX  OCTET STRING
                  MAX-ACCESS  read-only
                  STATUS  current -- was mandatory
                  DESCRIPTION
                  "Battery Backup Unit hardware VPD manufacturing ID.
                  For consistent results, view as a table and not as individual entries.
                              
                  NOTE: This MIB object is for BCS only."
                  ::= { bbuHardwareVpdEntry 3 }

        bbuHardwareVpdFruNumber  OBJECT-TYPE
                  SYNTAX  OCTET STRING
                  MAX-ACCESS  read-only
                  STATUS  current -- was mandatory
                  DESCRIPTION
                  "Battery Backup Unit hardware VPD FRU number.
                  For consistent results, view as a table and not as individual entries.
                              
                  NOTE: This MIB object is for BCS only."
                  ::= { bbuHardwareVpdEntry 4 }


        bbuHardwareVpdHardwareRevision  OBJECT-TYPE
                  SYNTAX  INTEGER
                  MAX-ACCESS  read-only
                  STATUS  current -- was mandatory
                  DESCRIPTION
                  "Battery Backup Unit hardware VPD hardware revision.
                  For consistent results, view as a table and not as individual entries.
                              
                  NOTE: This MIB object is for BCS only."
                  ::= { bbuHardwareVpdEntry 5 }

        bbuHardwareVpdUuid  OBJECT-TYPE
                  SYNTAX  OCTET STRING
                  MAX-ACCESS  read-only
                  STATUS  current -- was mandatory
                  DESCRIPTION
                  "Battery Backup Unit hardware VPD UUID.
                  For consistent results, view as a table and not as individual entries.
                              
                  NOTE: This MIB object is for BCS only."
                  ::= { bbuHardwareVpdEntry 8 }

        bbuHardwareVpdManufDate  OBJECT-TYPE
                  SYNTAX  OCTET STRING
                  MAX-ACCESS  read-only
                  STATUS  current -- was mandatory
                  DESCRIPTION
                  "Battery Backup Unit hardware VPD manufacture Date.
                  For consistent results, view as a table and not as individual entries.
                              
                  NOTE: This MIB object is for BCS only."
                  ::= { bbuHardwareVpdEntry 9 }

        bbuHardwareVpdPartNumber  OBJECT-TYPE
                  SYNTAX  OCTET STRING
                  MAX-ACCESS  read-only
                  STATUS  current -- was mandatory
                  DESCRIPTION
                  "Battery Backup Unit hardware VPD Part Number.
                  For consistent results, view as a table and not as individual entries.
                              
                  NOTE: This MIB object is for BCS only."
                  ::= { bbuHardwareVpdEntry 10 }

        bbuHardwareVpdFruSerial  OBJECT-TYPE
                  SYNTAX  OCTET STRING
                  MAX-ACCESS  read-only
                  STATUS  current -- was mandatory
                  DESCRIPTION
                  "Battery Backup Unit hardware VPD FRU Serial Number.
                  For consistent results, view as a table and not as individual entries.
                              
                  NOTE: This MIB object is for BCS only."
                  ::= { bbuHardwareVpdEntry 11 }
         
        bbuHardwareVpdManufacturingIDNumber  OBJECT-TYPE
                  SYNTAX  OCTET STRING
                  MAX-ACCESS  read-only
                  STATUS  current -- was mandatory
                  DESCRIPTION
                  "Battery Backup Unit hardware VPD manufacturer ID.
                  For consistent results, view as a table and not as individual entries."
                  ::= { bbuHardwareVpdEntry 12 }

        bbuHardwareVpdProductId  OBJECT-TYPE
                  SYNTAX  OCTET STRING
                  MAX-ACCESS  read-only
                  STATUS  current -- was mandatory
                  DESCRIPTION
                  "Battery Backup Unit hardware VPD product ID.
                  For consistent results, view as a table and not as individual entries."
                  ::= { bbuHardwareVpdEntry 13 }

        bbuHardwareVpdSubManufacturerId  OBJECT-TYPE
                  SYNTAX  OCTET STRING
                  MAX-ACCESS  read-only
                  STATUS  current -- was mandatory
                  DESCRIPTION
                  "Battery Backup Unit hardware VPD subsystem manufacturer ID.
                  For consistent results, view as a table and not as individual entries."
                  ::= { bbuHardwareVpdEntry 14 }

        bbuHardwareVpdClei  OBJECT-TYPE
                  SYNTAX  OCTET STRING
                  MAX-ACCESS  read-only
                  STATUS  current -- was mandatory
                  DESCRIPTION
                  "Battery Backup Unit hardware VPD Common 
                  Language Equipment Identifier (CLEI).
                  For consistent results, view as a table and not as individual entries."
                  ::= { bbuHardwareVpdEntry 15 }

      -- ********************************************************************************
      -- Reload VPD
      -- ********************************************************************************
        reloadVpdData OBJECT IDENTIFIER ::= { vpdInformation 23 }

        reloadAllVpdData OBJECT-TYPE
                    SYNTAX  INTEGER {
                        execute(1)
                    }
                    MAX-ACCESS  read-write
                    STATUS  current -- was mandatory
                    DESCRIPTION
                    "Reload all VPD data (firmware, hardware, MAC address, WWN/GUID and other Unique ID).
                    NOTE: The value returned for the GET command is meaningless."
                    ::= { reloadVpdData 1 }

        reloadFwVpdData OBJECT-TYPE
                    SYNTAX  INTEGER {
                        execute(1)
                    }
                    MAX-ACCESS  read-write
                    STATUS  current -- was mandatory
                    DESCRIPTION
                    "Reload firmware VPD data.
                    NOTE: The value returned for the GET command is meaningless."
                    ::= { reloadVpdData 2 }

        reloadHwVpdData OBJECT-TYPE
                    SYNTAX  INTEGER {
                        execute(1)
                    }
                    MAX-ACCESS  read-write
                    STATUS  current -- was mandatory
                    DESCRIPTION
                    "Reload hardware VPD data.
                    NOTE: The value returned for the GET command is meaningless."
                    ::= { reloadVpdData 3 }

        reloadMACAddress OBJECT-TYPE
                    SYNTAX  INTEGER {
                        execute(1)
                    }
                    MAX-ACCESS  read-write
                    STATUS  current -- was mandatory
                    DESCRIPTION
                    "Reload blade MAC addresses.
                    NOTE: The value returned for the GET command is meaningless."
                    ::= { reloadVpdData 4 }

        reloadWwnGuidVpdData OBJECT-TYPE
                    SYNTAX  INTEGER {
                        execute(1)
                    }
                    MAX-ACCESS  read-write
                    STATUS  current -- was mandatory
                    DESCRIPTION
                    "Reload blade and I/O module WWN/GUID and other VPD data.
                    NOTE: The value returned for the GET command is meaningless."
                    ::= { reloadVpdData 5 }


    -- *************************************************************************
    -- Passive Air Filter
    -- *************************************************************************

    airFilter  OBJECT IDENTIFIER ::= { monitors 22 }

      passiveAirFilter  OBJECT IDENTIFIER ::= { airFilter 1 }

        passiveAirFilterStatus    OBJECT-TYPE
                 SYNTAX  INTEGER {
                   disabled(0),
                   enabled(1)
                 }
                 MAX-ACCESS  read-write
                 STATUS  current -- was mandatory
                 DESCRIPTION
                 "Disable or enable the passive air filter.  When enabled, sending an enable will reset the replace date.
                  NOTE: This MIB object is for BladeCenter S and BladeCenter E Refresh only."
                 ::= { passiveAirFilter 1 }

        passiveAirFilterMonthFreq    OBJECT-TYPE
                 SYNTAX  INTEGER {
                   oneMonth(1),
                   threeMonths(3),
                   sixMonths(6)
                 }
                 MAX-ACCESS  read-write
                 STATUS  current -- was mandatory
                 DESCRIPTION
                 "The chassis environment.  1 month indicates high dust, 3 months indicates moderate dust and, 6 months indicates low dust.
                  NOTE: This MIB object is for BladeCenter S and BladeCenter E Refresh only."
                 ::= { passiveAirFilter 2 }

        passiveAirFilterReplaceDate OBJECT-TYPE
                 SYNTAX  OCTET STRING (SIZE(0..30))
                 MAX-ACCESS  read-only
                 STATUS  current -- was mandatory
                 DESCRIPTION
                 "The scheduled replacement date of the air filter.
                  NOTE: This MIB object is for BladeCenter S and BladeCenter E Refresh only."
                 ::= { passiveAirFilter 3 }

                    
      -- ********************************************************************************
      -- MM Security Settings
      -- ********************************************************************************
      securitySettings        OBJECT IDENTIFIER ::= { configureSP 3 }

      dataEncryption OBJECT-TYPE
                   SYNTAX  INTEGER {
                     disabled(0),
                     enabled(1)
                   }
                   MAX-ACCESS  read-write
                   STATUS  current -- was mandatory
                   DESCRIPTION
                   "If enabled, all confidential data will be encrypted. The default value is disabled.
                   NOTE: Once the data is encrypted, the only way to reverse this process is to
                   reset to default values."
                   ::= { securitySettings 1 }

      trespassWarning OBJECT-TYPE
                   SYNTAX  INTEGER {
                     disabled(0),
                     enabled(1)
                   }
                   MAX-ACCESS  read-write
                   STATUS  current -- was mandatory
                   DESCRIPTION
                   "If enabled, a customizable trespass warning message is displayed via the Web 
                   and CLI interfaces."
                   ::= { securitySettings 2 }

      -- ********************************************************************************
      -- MM Clock
      -- ********************************************************************************
      spClock        OBJECT IDENTIFIER ::= { configureSP 4 }

       spClockDateAndTimeSetting OBJECT-TYPE
                    SYNTAX  OCTET STRING
                    MAX-ACCESS  read-write
                    STATUS  current -- was mandatory
                    DESCRIPTION
                    "MM clock date and time setting.
                    A date-time specification for the local time of day.
                    For example to set the date and time to
                    March 4, 2001 at 06:00:00AM, set the value to:'03/04/2001,06:00:00'.
                    field  contents         range
                    _____  ________         _____
                      1     month           01..12
                      2     separator       '/'
                      3     day             01..31
                      4     separator       '/'
                      5     year            2000..2089
                      6     separator       ','
                      7     hour            00..23
                      8     separator       ':'
                      9     minutes         00..59
                      10    separator       ':'
                      11    seconds         00..59
                    "
                    ::= { spClock  1 }

       spClockTimezoneSetting OBJECT-TYPE
                    SYNTAX  OCTET STRING
                    MAX-ACCESS  read-write
                    STATUS  current -- was mandatory
                    DESCRIPTION
                    "MM clock Greenwich Mean Time(GMT) offset and Daylight Saving Time(DST)
                    settings.

                    The following table lists GMT offsets and associated DST
                    information.  DST is not observed in time zones where
                    the 'Observe DST' value does not contain 'yes' in the table.
                    Also, note that in some cases additional information
                    is required to determine the clock adjustment when DST is
                    observed.  The additional information is required when the
                    GMT offset being written is +2:00 or +10:00.

                    Examples
                          -to set the GMT offset to +3:30,
                           set the value to:'+3:30,no'

                          -for Eastern Standard Time and observing DST,
                           set the value to:'-5:00,yes'

                          -for Egypt and observing DST,
                           set the value to:'+2:00,yes,6'


                     GMT    Observe  Additional
                    Offset    DST?    DST value
                    ______  _______  __________
                     +0:00  yes|no
                     +1:00  yes|no
                     +2:00  yes|no   When 'Observe DST?' value is 'yes':
                                     5 (for E.Europe)
                                     4 (for GTB)
                                     6 (for Egypt)
                                     7 (for FLE)
                     +3:00  yes|no
                     +3:30  yes|no
                     +4:00  no
                     +4:30  no
                     +5:00  yes|no
                     +5:30  no
                     +6:00  no
                     +7:00  no
                     +8:00  yes|no
                     +9:00  yes|no
                     +9:30  yes|no   When 'Observe DST?' value is 'yes':
                                     10 (for South AUS)
                                     9  (for other locations)
                    +10:00  yes|no   When 'Observe DST?' value is 'yes':
                                     9  (for AUS Eastern)
                                     10 (for TAS,ACT,NSW,VIC)
                                     4  (for Vladivostok)
                    +11:00  no
                    +12:00  yes|no
                    -12:00  no
                    -11:00  no
                    -10:00  no
                     -9:00  yes|no   When 'Observe DST?' value is 'yes':
                                     12 (for USA and Canada)
                                     1 (for other locations)
                     -8:00  yes|no   When 'Observe DST?' value is 'yes':
                                     12 (for USA and Canada)
                                     1 (for other locations)
                     -7:00  yes|no   When 'Observe DST?' value is 'yes':
                                     12 (for USA and Canada)
                                     1 (for other locations)
                     -6:00  yes|no   When 'Observe DST?' value is 'yes':
                                     12 (for USA and Canada)
                                     1 (for other locations)
                     -5:00  yes|no   When 'Observe DST?' value is 'yes':
                                     12 (for USA and Canada)
                                     1 (for other locations)
                     -4:00  yes|no   When 'Observe DST' value is 'yes':
                                     12 (for Canada)
                                     1 (for other locations)
                     -3:30  yes|no
                     -3:00  yes|no
                     -2:00  yes|no
                     -1:00  yes|no
                     "
                    ::= { spClock  2 }


      -- ********************************************************************************
      -- MM identification
      -- ********************************************************************************
      spIdentification        OBJECT IDENTIFIER ::= { configureSP 5 }

       spTxtId      OBJECT-TYPE
                    SYNTAX  OCTET STRING (SIZE(0..16))
                    MAX-ACCESS  read-write
                    STATUS  current -- was mandatory
                    DESCRIPTION
                    "MM text ID.  
                    NOTE: Do not put any 'space characters' at end of the ID."
                    ::= { spIdentification 1 }

      -- ********************************************************************************
      -- Network Configuration
      -- ********************************************************************************
      networkConfiguration  OBJECT IDENTIFIER ::= { configureSP 9 }

       -- ********************************************************************************
       -- Network Interfaces
       -- ********************************************************************************
       networkInterfaces  OBJECT IDENTIFIER ::= { networkConfiguration 1 }
        -- ********************************************************************************
        -- Ethernet Interface 1
        -- ********************************************************************************
        extEthernetInterface  OBJECT IDENTIFIER ::= { networkInterfaces 1 }

         extEthernetInterfaceType OBJECT-TYPE
                      SYNTAX  OCTET STRING (SIZE(0..16))
                      MAX-ACCESS  read-only
                      STATUS  current -- was mandatory
                      DESCRIPTION
                      "The type of interface.  Indicates 'Ethernet-1'."
                      ::= { extEthernetInterface 1 }

         extEthernetInterfaceHostName  OBJECT-TYPE
                      SYNTAX  OCTET STRING (SIZE(0..64))
                      MAX-ACCESS  read-write
                      STATUS  current -- was mandatory
                      DESCRIPTION
                      "Contains the 64 byte null terminated DNS host name for this
                      interface."
                      ::= { extEthernetInterface 3 }

         extEthernetInterfaceIPAddress   OBJECT-TYPE
                      SYNTAX  IpAddress
                      MAX-ACCESS  read-write
                      STATUS  current -- was mandatory
                      DESCRIPTION
                      "Contains the IP address for the ethernet interface."
                      ::= { extEthernetInterface 4 }

         extEthernetInterfaceDataRate   OBJECT-TYPE
                      SYNTAX  INTEGER {
                        enet10Megabit(3),
                        enet100Megabit(4),
                        autoSpeed(5)
                      }
                      MAX-ACCESS  read-write
                      STATUS  current -- was mandatory
                      DESCRIPTION
                      "Specifies the data transfer rate to be used over the ethernet
                      interface:  10Mb, 100Mb, or Auto."
                      ::= { extEthernetInterface 5 }

         extEthernetInterfaceDuplexSetting  OBJECT-TYPE
                      SYNTAX  INTEGER {
                        fullDuplex(1),
                        halfDuplex(2),
                        autoDuplex(3)
                      }
                      MAX-ACCESS  read-write
                      STATUS  current -- was mandatory
                      DESCRIPTION
                      "Specifies the duplex settings for the data transfer rate to be used over
                      the ethernet interface:  Half, Full, or Auto."
                      ::= { extEthernetInterface 6 }

         extEthernetInterfaceLAA OBJECT-TYPE
                      SYNTAX  OCTET STRING (SIZE(17))
                      MAX-ACCESS  read-write
                      STATUS  current -- was mandatory
                      DESCRIPTION
                      "Specifies the locally administered MAC address.  The locally administered
                      address must be a hexadecimal value between 000000000000 - FFFFFFFFFFFF.  This
                      value must be in the form XX:XX:XX:XX:XX:XX where 'X' is a number between 0 - 9 and
                      A - F.  This MM subsystem does not allow use of a multicast address.  A multicast
                      address has the least significant bit of the first byte set to a 1.  The first
                      byte must, therefore, be an even number."
                      ::= { extEthernetInterface 7 }

         extEthernetInterfaceDhcpEnabled  OBJECT-TYPE
                      SYNTAX  INTEGER {
                        dhcpDisabled(0),
                        dhcpEnabled(1),
                        tryDhcpThenTryStatic(2)
                      }
                      MAX-ACCESS  read-write
                      STATUS  current -- was mandatory
                      DESCRIPTION
                      "Disable or enable DHCP on this interface."
                      ::= { extEthernetInterface 8 }

         extEthernetInterfaceGatewayIPAddress   OBJECT-TYPE
                      SYNTAX  IpAddress
                      MAX-ACCESS  read-write
                      STATUS  current -- was mandatory
                      DESCRIPTION
                      "Contains the IP address of the gateway/router for the ethernet
                       interface."
                      ::= { extEthernetInterface 9 }

         extEthernetInterfaceBIA OBJECT-TYPE
                      SYNTAX  OCTET STRING (SIZE(17))
                      MAX-ACCESS  read-only
                      STATUS  current -- was mandatory
                      DESCRIPTION
                      "Specifies the burned-in MAC (BIA) address."
                      ::= { extEthernetInterface 10 }

         extEthernetInterfaceMTU   OBJECT-TYPE
                      SYNTAX  INTEGER
                      MAX-ACCESS  read-write
                      STATUS  current -- was mandatory
                      DESCRIPTION
                      "Contains the Maximum Transmission Unit(MTU) for the ethernet
                      interface"
                      ::= { extEthernetInterface 13 }

         extEthernetInterfaceSubnetMask   OBJECT-TYPE
                      SYNTAX  IpAddress
                      MAX-ACCESS  read-write
                      STATUS  current -- was mandatory
                      DESCRIPTION
                      "Contains the subnet mask for the ethernet interface"
                      ::= { extEthernetInterface 14 }

         -- ********************************************************************************
         -- DHCP Server Assigned Settings for ethernet interface 1
         -- ********************************************************************************

         dhcpEthernetInterface  OBJECT IDENTIFIER ::= { extEthernetInterface 16 }

          dhcpHostName  OBJECT-TYPE
                       SYNTAX  OCTET STRING (SIZE(0..64))
                       MAX-ACCESS  read-only
                       STATUS  current -- was mandatory
                       DESCRIPTION
                       "Contains the 64 byte null terminated DNS host name for this
                       interface, assigned by the DHCP server."
                       ::= { dhcpEthernetInterface 1 }

          dhcpIPAddress   OBJECT-TYPE
                       SYNTAX  IpAddress
                       MAX-ACCESS  read-only
                       STATUS  current -- was mandatory
                       DESCRIPTION
                       "Contains the IP address for the ethernet interface,
                       assigned by the DHCP server."
                       ::= { dhcpEthernetInterface 2 }

          dhcpGatewayIPAddress   OBJECT-TYPE
                       SYNTAX  IpAddress
                       MAX-ACCESS  read-only
                       STATUS  current -- was mandatory
                       DESCRIPTION
                       "Contains the IP address of the gateway/router for the ethernet
                        interface, assigned by the DHCP server."
                       ::= { dhcpEthernetInterface 3 }

          dhcpSubnetMask   OBJECT-TYPE
                       SYNTAX  IpAddress
                       MAX-ACCESS  read-only
                       STATUS  current -- was mandatory
                       DESCRIPTION
                       "Contains the Subnet Mask for the ethernet
                       interface, assigned by the DHCP server."
                       ::= { dhcpEthernetInterface 4 }

          dhcpDomainName  OBJECT-TYPE
                       SYNTAX  OCTET STRING (SIZE(0..64))
                       MAX-ACCESS  read-only
                       STATUS  current -- was mandatory
                       DESCRIPTION
                       "Contains the 64 byte null terminated Domain Name for this
                       interface, assigned by the DHCP server."
                       ::= { dhcpEthernetInterface 5 }

          dhcpDHCPServer  OBJECT-TYPE
                       SYNTAX  IpAddress
                       MAX-ACCESS  read-only
                       STATUS  current -- was mandatory
                       DESCRIPTION
                       "Contains the DHCP server IP address used to acquire the
                       DHCP settings."
                       ::= { dhcpEthernetInterface 6 }

          dhcpPrimaryDNSServer  OBJECT-TYPE
                       SYNTAX  IpAddress
                       MAX-ACCESS  read-only
                       STATUS  current -- was mandatory
                       DESCRIPTION
                       "Contains the Primary DNS server, assigned by the DHCP server."
                       ::= { dhcpEthernetInterface 7 }

          dhcpSecondaryDNSServer  OBJECT-TYPE
                       SYNTAX  IpAddress
                       MAX-ACCESS  read-only
                       STATUS  current -- was mandatory
                       DESCRIPTION
                       "Contains the Secondary DNS server, assigned by the DHCP server."
                       ::= { dhcpEthernetInterface 8 }

          dhcpTertiaryDNSServer  OBJECT-TYPE
                       SYNTAX  IpAddress
                       MAX-ACCESS  read-only
                       STATUS  current -- was mandatory
                       DESCRIPTION
                       "Contains the tertiary DNS server, assigned by the DHCP server."
                       ::= { dhcpEthernetInterface 9 }

        -- ********************************************************************************
        -- PPP Interface 1
        -- ********************************************************************************
        intEthernetInterface  OBJECT IDENTIFIER ::= { networkInterfaces 2 }

         intEthernetInterfaceType     OBJECT-TYPE
                      SYNTAX  OCTET STRING (SIZE(0..16))
                      MAX-ACCESS  read-only
                      STATUS  current -- was mandatory
                      DESCRIPTION
                      "The type of interface.  Indicates 'PPP-1'."
                      ::= { intEthernetInterface 1 }

         intEthernetInterfaceEnabled  OBJECT-TYPE
                      SYNTAX  INTEGER {
                        interfaceDisabled(0),
                        interfaceEnabled(1)
                      }
                      MAX-ACCESS  read-write
                      STATUS  current -- was mandatory
                      DESCRIPTION
                      "Disable or enable the internal ethernet interface.
                      NOTE: To alter any of the configuration settings for the
                      ethernet interface, the following procedure should be used:
                      (1) This object should be set to 'interfaceDisabled'
                      (2) Make the modifications to other settings
                      (3) This object should be set to 'interfaceEnabled'
                      (4) Restart the management module

                      Also note that when attempting to enable this interface, the
                      remote IP address is verified to be nonzero.  If this verification
                      fails, an error response will be returned and the internal ethernet
                      interface will be left disabled."
                      ::= { intEthernetInterface 2 }

         intEthernetInterfaceLocalIPAddress   OBJECT-TYPE
                      SYNTAX  IpAddress
                      MAX-ACCESS  read-write
                      STATUS  current -- was mandatory
                      DESCRIPTION
                      "Contains the IP address for the MM side of the internal ethernet link."
                      ::= { intEthernetInterface 4 }

         intEthernetInterfaceDataRate   OBJECT-TYPE
                      SYNTAX  INTEGER {
                        enet10Megabit(3),
                        enet100Megabit(4),
                        autoSpeed(5)
                      }
                      MAX-ACCESS  read-only
                      STATUS  current -- was mandatory
                      DESCRIPTION
                      "Specifies the data transfer rate to be used over the ethernet
                      interface:  10Mb, 100Mb, or Auto."
                      ::= { intEthernetInterface 5 }

         intEthernetInterfaceDuplexSetting  OBJECT-TYPE
                      SYNTAX  INTEGER {
                        fullDuplex(1),
                        halfDuplex(2),
                        autoDuplex(3)
                      }
                      MAX-ACCESS  read-only
                      STATUS  current -- was mandatory
                      DESCRIPTION
                      "Specifies the duplex settings for the data transfer rate to be used over
                      the ethernet interface:  Half, Full, or Auto."
                      ::= { intEthernetInterface 6 }

         intEthernetInterfaceLAA OBJECT-TYPE
                      SYNTAX  OCTET STRING (SIZE(17))
                      MAX-ACCESS  read-write
                      STATUS  current -- was mandatory
                      DESCRIPTION
                      "Specifies the locally administered MAC address.  The locally administered
                      address must be a hexadecimal value between 000000000000 - FFFFFFFFFFFF.  This
                      value must be in the form XX:XX:XX:XX:XX:XX where 'X' is a number between 0 - 9 and
                      A - F.  This MM subsystem does not allow use of a multicast address.  A multicast
                      address has the least significant bit of the first byte set to a 1.  The first
                      byte must, therefore, be an even number."
                      ::= { intEthernetInterface 7 }

         intEthernetInterfaceGatewayIPAddress   OBJECT-TYPE
                      SYNTAX  IpAddress
                      MAX-ACCESS  read-write
                      STATUS  current -- was mandatory
                      DESCRIPTION
                      "Contains the IP address of the gateway/router for the ethernet
                       interface."
                      ::= { intEthernetInterface 9 }

         intEthernetInterfaceBIA OBJECT-TYPE
                      SYNTAX  OCTET STRING (SIZE(17))
                      MAX-ACCESS  read-only
                      STATUS  current -- was mandatory
                      DESCRIPTION
                      "Specifies the burned-in MAC (BIA) address."
                      ::= { intEthernetInterface 10 }

         intEthernetInterfaceMTU   OBJECT-TYPE
                      SYNTAX  INTEGER
                      MAX-ACCESS  read-only
                      STATUS  current -- was mandatory
                      DESCRIPTION
                      "Contains the Maximum Transmission Unit (MTU) for the ethernet
                      interface"
                      ::= { intEthernetInterface 13 }

         intEthernetInterfaceSubnetMask   OBJECT-TYPE
                      SYNTAX  IpAddress
                      MAX-ACCESS  read-write
                      STATUS  current -- was mandatory
                      DESCRIPTION
                      "Contains the subnet mask for the ethernet interface."
                      ::= { intEthernetInterface 14 }
         -- ********************************************************************************
        -- Standby Ethernet Interface 1
        -- ********************************************************************************
         standbyExtEthernetInterface  OBJECT IDENTIFIER ::= { networkInterfaces 3 }
         standbyExtEthernetInterfaceType OBJECT-TYPE
                      SYNTAX  OCTET STRING (SIZE(0..16))
                      MAX-ACCESS  read-only
                      STATUS  current -- was mandatory
                      DESCRIPTION
                      "The type of interface.  Indicates 'Ethernet-1'.

                      NOTE: This MIB object is only applicable to systems with a standby MM."
                      ::= { standbyExtEthernetInterface 1 }

         standbyExtEthernetInterfaceHostName  OBJECT-TYPE
                      SYNTAX  OCTET STRING (SIZE(0..64))
                      MAX-ACCESS  read-write
                      STATUS  current -- was mandatory
                      DESCRIPTION
                      "Contains the 64 byte null terminated DNS host name for this
                      interface.
                      
                      NOTE: This MIB object is only applicable to systems with a standby MM."
                      ::= { standbyExtEthernetInterface 3 }

         standbyExtEthernetInterfaceIPAddress   OBJECT-TYPE
                      SYNTAX  IpAddress
                      MAX-ACCESS  read-write
                      STATUS  current -- was mandatory
                      DESCRIPTION
                      "Contains the IP address for the ethernet interface.
                      
                      NOTE: This MIB object is only applicable to systems with a standby MM."
                      ::= { standbyExtEthernetInterface 4 }

         standbyExtEthernetInterfaceDataRate   OBJECT-TYPE
                      SYNTAX  INTEGER {
                        enet10Megabit(3),
                        enet100Megabit(4),
                        autoSpeed(5)
                      }
                      MAX-ACCESS  read-write
                      STATUS  current -- was mandatory
                      DESCRIPTION
                      "Specifies the data transfer rate to be used over the ethernet
                      interface:  10Mb, 100Mb, or Auto.
                      
                      NOTE: This MIB object is only applicable to systems with a standby MM."
                      ::= { standbyExtEthernetInterface 5 }

         standbyExtEthernetInterfaceDuplexSetting  OBJECT-TYPE
                      SYNTAX  INTEGER {
                        fullDuplex(1),
                        halfDuplex(2),
                        autoDuplex(3)
                      }
                      MAX-ACCESS  read-write
                      STATUS  current -- was mandatory
                      DESCRIPTION
                      "Specifies the duplex settings for the data transfer rate to be used over
                      the ethernet interface:  Half, Full, or Auto.
                      
                      NOTE: This MIB object is only applicable to systems with a standby MM."
                      ::= { standbyExtEthernetInterface 6 }

         standbyExtEthernetInterfaceLAA OBJECT-TYPE
                      SYNTAX  OCTET STRING (SIZE(17))
                      MAX-ACCESS  read-write
                      STATUS  current -- was mandatory
                      DESCRIPTION
                      "Specifies the locally administered MAC address.  The locally administered
                      address must be a hexadecimal value between 000000000000 - FFFFFFFFFFFF.  
                      This value must be in the form XX:XX:XX:XX:XX:XX where 'X' is a number between 0 - 9 and A - F.  
                      This MM subsystem does not allow use of a multicast address.  
                      A multicast address has the least significant bit of the first byte set to a 1.  The first
                      byte must, therefore, be an even number.
                      
                      NOTE: This MIB object is only applicable to systems with a standby MM."
                      ::= { standbyExtEthernetInterface 7 }

         standbyExtEthernetInterfaceDhcpEnabled  OBJECT-TYPE
                      SYNTAX  INTEGER {
                        dhcpDisabled(0),
                        dhcpEnabled(1),
                        tryDhcpThenTryStatic(2)
                      }
                      MAX-ACCESS  read-write
                      STATUS  current -- was mandatory
                      DESCRIPTION
                      "Disable or enable DHCP on this interface.
                      
                      NOTE: This MIB object is only applicable to systems with a standby MM."
                      ::= { standbyExtEthernetInterface 8 }

         standbyExtEthernetInterfaceGatewayIPAddress   OBJECT-TYPE
                      SYNTAX  IpAddress
                      MAX-ACCESS  read-write
                      STATUS  current -- was mandatory
                      DESCRIPTION
                      "Contains the IP address of the gateway/router for the ethernet
                       interface.
                       
                      NOTE: This MIB object is only applicable to systems with a standby MM."
                      ::= { standbyExtEthernetInterface 9 }

         standbyExtEthernetInterfaceBIA OBJECT-TYPE
                      SYNTAX  OCTET STRING (SIZE(17))
                      MAX-ACCESS  read-only
                      STATUS  current -- was mandatory
                      DESCRIPTION
                      "Specifies the burned-in MAC (BIA) address.
                      
                      NOTE: This MIB object is only applicable to systems with a standby MM."
                      ::= { standbyExtEthernetInterface 10 }

         standbyExtEthernetInterfaceMTU   OBJECT-TYPE
                      SYNTAX  INTEGER
                      MAX-ACCESS  read-write
                      STATUS  current -- was mandatory
                      DESCRIPTION
                      "Contains the Maximum Transmission Unit (MTU) for the ethernet
                      interface.
                      
                      NOTE: This MIB object is only applicable to systems with a standby MM."
                      ::= { standbyExtEthernetInterface 13 }

         standbyExtEthernetInterfaceSubnetMask   OBJECT-TYPE
                      SYNTAX  IpAddress
                      MAX-ACCESS  read-write
                      STATUS  current -- was mandatory
                      DESCRIPTION
                      "Contains the subnet mask for the ethernet interface.
                      
                      NOTE: This MIB object is only applicable to systems with a standby MM."
                      ::= { standbyExtEthernetInterface 14 }

         advancedFailover  OBJECT-TYPE
                      SYNTAX  INTEGER{
                        off(0),
                        ipnoswap(1),
                        ipswap(2)
                      }
                      MAX-ACCESS  read-write
                      STATUS  current -- was mandatory
                      DESCRIPTION
                      "User can enable advanced failover.
                       off : no standby network interface
                       ipswap: Standby network interface, swap IPs during failover
                       ipnoswap: Standby network interface, no swap IPs during failover.
                       
                      NOTE: This MIB object is only applicable to systems with a standby MM."
                      ::= { standbyExtEthernetInterface 15 }

         -- ********************************************************************************
         -- DHCP Server Assigned Settings for standby ethernet interface 1
         -- ********************************************************************************

         standbyDhcpEthernetInterface  OBJECT IDENTIFIER ::= { standbyExtEthernetInterface 16 }

          standbyDhcpHostName  OBJECT-TYPE
                       SYNTAX  OCTET STRING (SIZE(0..64))
                       MAX-ACCESS  read-only
                       STATUS  current -- was mandatory
                       DESCRIPTION
                       "Contains the 64 byte null terminated DNS host name for this
                       interface, assigned by the DHCP server.
                       
                       NOTE: This MIB object is only applicable to systems with a standby MM."
                       ::= { standbyDhcpEthernetInterface 1 }

          standbyDhcpIPAddress   OBJECT-TYPE
                       SYNTAX  IpAddress
                       MAX-ACCESS  read-only
                       STATUS  current -- was mandatory
                       DESCRIPTION
                       "Contains the IP address for the ethernet interface,
                       assigned by the DHCP server.
                       
                       NOTE: This MIB object is only applicable to systems with a standby MM."
                       ::= { standbyDhcpEthernetInterface 2 }

          standbyDhcpGatewayIPAddress   OBJECT-TYPE
                       SYNTAX  IpAddress
                       MAX-ACCESS  read-only
                       STATUS  current -- was mandatory
                       DESCRIPTION
                       "Contains the IP address of the gateway/router for the ethernet
                        interface, assigned by the DHCP server.
                        
                       NOTE: This MIB object is only applicable to systems with a standby MM."
                       ::= { standbyDhcpEthernetInterface 3 }

          standbyDhcpSubnetMask   OBJECT-TYPE
                       SYNTAX  IpAddress
                       MAX-ACCESS  read-only
                       STATUS  current -- was mandatory
                       DESCRIPTION
                       "Contains the Subnet Mask for the ethernet
                       interface, assigned by the DHCP server.
                       
                       NOTE: This MIB object is only applicable to systems with a standby MM."
                       ::= { standbyDhcpEthernetInterface 4 }

          standbyDhcpDomainName  OBJECT-TYPE
                       SYNTAX  OCTET STRING (SIZE(0..64))
                       MAX-ACCESS  read-only
                       STATUS  current -- was mandatory
                       DESCRIPTION
                       "Contains the 64 byte null terminated Domain Name for this
                       interface, assigned by the DHCP server.
                       
                       NOTE: This MIB object is only applicable to systems with a standby MM."
                       ::= { standbyDhcpEthernetInterface 5 }

          standbyDhcpDHCPServer  OBJECT-TYPE
                       SYNTAX  IpAddress
                       MAX-ACCESS  read-only
                       STATUS  current -- was mandatory
                       DESCRIPTION
                       "Contains the DHCP server IP address used to acquire the
                       DHCP settings.

                       NOTE: This MIB object is only applicable to systems with a standby MM."
                       ::= { standbyDhcpEthernetInterface 6 }

          standbyDhcpPrimaryDNSServer  OBJECT-TYPE
                       SYNTAX  IpAddress
                       MAX-ACCESS  read-only
                       STATUS  current -- was mandatory
                       DESCRIPTION
                       "Contains the Primary DNS server, assigned by the DHCP server.
                       
                       NOTE: This MIB object is only applicable to systems with a standby MM."
                       ::= { standbyDhcpEthernetInterface 7 }

          standbyDhcpSecondaryDNSServer  OBJECT-TYPE
                       SYNTAX  IpAddress
                       MAX-ACCESS  read-only
                       STATUS  current -- was mandatory
                       DESCRIPTION
                       "Contains the Secondary DNS server, assigned by the DHCP server.
                       
                       NOTE: This MIB object is only applicable to systems with a standby MM."
                       ::= { standbyDhcpEthernetInterface 8 }

          standbyDhcpTertiaryDNSServer  OBJECT-TYPE
                       SYNTAX  IpAddress
                       MAX-ACCESS  read-only
                       STATUS  current -- was mandatory
                       DESCRIPTION
                       "Contains the tertiary DNS server, assigned by the DHCP server.
                       
                       NOTE: This MIB object is only applicable to systems with a standby MM."
                       ::= { standbyDhcpEthernetInterface 9 }

       -- ********************************************************************************
       -- TCP/IP Protocol Configuration
       -- ********************************************************************************
       tcpProtocols  OBJECT IDENTIFIER ::= { networkConfiguration 3 }

        -- ********************************************************************************
        -- SNMP Agent Configuration
        -- ********************************************************************************
        snmpAgentConfig  OBJECT IDENTIFIER ::= { tcpProtocols 1 }


         snmpSystemContact     OBJECT-TYPE
                      SYNTAX  OCTET STRING (SIZE(0..48))
                      MAX-ACCESS  read-write
                      STATUS  current -- was mandatory
                      DESCRIPTION
                      "A NULL terminated 48 byte string that contains the
                      SNMP agent contact name."
                      ::= { snmpAgentConfig 1 }

         snmpSystemLocation     OBJECT-TYPE
                      SYNTAX  OCTET STRING (SIZE(0..48))
                      MAX-ACCESS  read-write
                      STATUS  current -- was mandatory
                      DESCRIPTION
                      "A NULL terminated 48 byte string that contains the
                      SNMP agent location name."
                      ::= { snmpAgentConfig 2 }

         snmpSystemAgentTrapsDisable  OBJECT-TYPE
                      SYNTAX  INTEGER {
                        trapsEnabled(0),
                        trapsDisabled(1)
                      }
                      MAX-ACCESS  read-write
                      STATUS  current -- was mandatory
                      DESCRIPTION
                      "Disable or enable SNMP traps."
                      ::= { snmpAgentConfig 3 }

         -- ********************************************************************************
         -- SNMP Agent Community Configuration
         -- ********************************************************************************
         snmpAgentCommunityConfig  OBJECT IDENTIFIER ::= { snmpAgentConfig 4 }


          -- ********************************************************************************
          -- SNMP Community Configuration table
          -- ********************************************************************************

          snmpCommunityTable  OBJECT-TYPE
                                SYNTAX  SEQUENCE OF SnmpCommunityEntry
                                MAX-ACCESS  not-accessible
                                STATUS  current -- was mandatory
                                DESCRIPTION
                                "Table of SNMP Community entries"
                                ::= {  snmpAgentCommunityConfig 1 }

          snmpCommunityEntry  OBJECT-TYPE
                                SYNTAX  SnmpCommunityEntry
                                MAX-ACCESS  not-accessible
                                STATUS  current -- was mandatory
                                DESCRIPTION
                                "SNMP community entries"
                                INDEX { snmpCommunityEntryIndex }
                                ::= { snmpCommunityTable 1 }

          SnmpCommunityEntry ::= SEQUENCE {
                       snmpCommunityEntryIndex INTEGER,
                       snmpCommunityEntryCommunityName OCTET STRING,
                       snmpCommunityEntryCommunityIpAddress1 OCTET STRING,
                       snmpCommunityEntryCommunityIpAddress2 OCTET STRING,
                       snmpCommunityEntryCommunityIpAddress3 OCTET STRING,
                       snmpCommunityEntryCommunityViewType INTEGER
                       }


          snmpCommunityEntryIndex   OBJECT-TYPE
                                    SYNTAX  INTEGER(0..255)
                                    MAX-ACCESS  read-only
                                    STATUS  current -- was mandatory
                                    DESCRIPTION
                                    "Index for SNMP Agent Community entry."
                                    ::= { snmpCommunityEntry 1 }

          snmpCommunityEntryCommunityName  OBJECT-TYPE
                                    SYNTAX  OCTET STRING (SIZE(0..15))
                                    MAX-ACCESS  read-write
                                    STATUS  current -- was mandatory
                                    DESCRIPTION
                                    "SNMP Community entry name.  If an IP address of 0.0.0.0 is 
                                    configured for the first host name in the first community,
                                    any hosts can query MIB objects using the specified community
                                    name on a Get.  Likewise, on a Set, any host can have write access.
                                    NOTE: Set snmpv1SystemAgentEnable to disabled before performing 
                                    a Set of this object. IP address of 0.0.0.0 is allowed only for 
                                    the first host name in the first community and only if the access 
                                    type of this community is configured as Get or Set."
                                    ::= { snmpCommunityEntry 2 }

          snmpCommunityEntryCommunityIpAddress1  OBJECT-TYPE
                                    SYNTAX  OCTET STRING (SIZE(0..63))
                                    MAX-ACCESS  read-write
                                    STATUS  current -- was mandatory
                                    DESCRIPTION
                                    "SNMP Community IP address or host name.
                                    Can either be a dotted decimal IP string (e.g. 9.37.44.2)
                                    or if DNS is enabled a host name.  If an IP address of 
                                    0.0.0.0 is configured for the first host name in the first 
                                    community, any hosts can query MIB objects using the specified
                                    community name.  Likewise, on a Set, any host can have write access.
                                    NOTE: Set snmpv1SystemAgentEnable to disabled before performing 
                                    a Set of this object. IP address of 0.0.0.0 is allowed only for 
                                    the first host name in the first community and only if the access 
                                    type of this community is configured as Get or Set."
                                    ::= { snmpCommunityEntry 3 }

          snmpCommunityEntryCommunityIpAddress2  OBJECT-TYPE
                                    SYNTAX  OCTET STRING (SIZE(0..63))
                                    MAX-ACCESS  read-write
                                    STATUS  current -- was mandatory
                                    DESCRIPTION
                                    "SNMP Community IP address or host name.
                                    Can either be a dotted decimal IP string (e.g. 9.37.44.2)
                                    or, if DNS is enabled, a host name.
                                    NOTE: Set snmpv1SystemAgentEnable to disabled before performing 
                                    a Set of this object."

                                    ::= { snmpCommunityEntry 4 }

          snmpCommunityEntryCommunityIpAddress3  OBJECT-TYPE
                                    SYNTAX  OCTET STRING (SIZE(0..63))
                                    MAX-ACCESS  read-write
                                    STATUS  current -- was mandatory
                                    DESCRIPTION
                                    "SNMP Community IP address or host name.
                                    Can either be a dotted decimal IP string (e.g. 9.37.44.2)
                                    or if DNS is enabled a host name.
                                    NOTE: Set snmpv1SystemAgentEnable to disabled before performing 
                                    a Set of this object."

                                    ::= { snmpCommunityEntry 5 }


          snmpCommunityEntryCommunityViewType  OBJECT-TYPE
                                     SYNTAX  INTEGER {
                                     read-Traps(1),
                                     write-Read-Traps(2),
                                     traps-Only(3)
                                     }
                                     MAX-ACCESS  read-write
                                     STATUS  current -- was mandatory
                                     DESCRIPTION
                                     "Access Level of the SNMPv1 managers.  Note this parameter 
                                     is set for each community.  Therefore all three managers 
                                     in the same community have the same access level."
                                     ::= { snmpCommunityEntry 6 }
                                    
         snmpv1SystemAgentEnable  OBJECT-TYPE
                      SYNTAX  INTEGER {
                        disabled(0),
                        enabled(1)
                      }
                      MAX-ACCESS  read-write
                      STATUS  current -- was mandatory
                      DESCRIPTION
                      "Disable or enable the SNMPv1 agent.

                      NOTE: Restart the management module if this MIB object is changed 
                      with respect to the value at system bootup time.  For example the 
                      SNMPv1 agent was set to disabled at system bootup time and now 
                      it is enabled.  Then restarting the remote supervisor adaptor is 
                      required.  

                      Also note that when attempting to enable this agent,
                      the following are verified:
                      (1) Is there a valid system contact
                      (2) Is there a valid system name
                      (3) Is there at least one valid community name and for that
                      community name is there one valid IP address or hostname
                      (4) Are all defined community names unique

                      If this verification fails an error response will be returned
                      and the SNMPv1 agent will be left disabled."
                      ::= { snmpAgentConfig 5 }

         snmpv3SystemAgentEnable  OBJECT-TYPE
                      SYNTAX  INTEGER {
                        disabled(0),
                        enabled(1)
                      }
                      MAX-ACCESS  read-write
                      STATUS  current -- was mandatory
                      DESCRIPTION
                      "Disable or enable the SNMPv3 agent.
                      
                      NOTE: Restart the management module if this MIB object is changed 
                      with respect to the value at system bootup time.  For example the 
                      SNMPv3 agent was set to disabled at system bootup time and now 
                      it is enabled.  Then restarting the remote supervisor adaptor is 
                      required.  

                      Also note that when attempting to enable this agent,
                      the following are verified:
                      (1) Is there a valid system contact?
                      (2) Is there a valid system name?

                      If this verification fails an error response will be returned
                      and the SNMPv3 agent will be left disabled."

                      ::= { snmpAgentConfig 6 }

         -- ********************************************************************************
         -- SNMP Agent User Profile Configuration
         -- ********************************************************************************
         
         snmpAgentUserProfileConfig  OBJECT IDENTIFIER ::= { snmpAgentConfig 9 }


          -- ********************************************************************************
          -- SNMP User Profile Configuration table
          -- ********************************************************************************

          snmpUserProfileTable  OBJECT-TYPE
                                SYNTAX  SEQUENCE OF SnmpUserProfileEntry
                                MAX-ACCESS  not-accessible
                                STATUS  current -- was mandatory
                                DESCRIPTION
                                "Table of SNMPv3 User Profile entries"
                                ::= {  snmpAgentUserProfileConfig 1 }

          snmpUserProfileEntry  OBJECT-TYPE
                                SYNTAX  SnmpUserProfileEntry
                                MAX-ACCESS  not-accessible
                                STATUS  current -- was mandatory
                                DESCRIPTION
                                "SNMP User Profile entries"
                                INDEX { snmpUserProfileEntryIndex }
                                ::= { snmpUserProfileTable 1 }

          SnmpUserProfileEntry ::= SEQUENCE {
                       snmpUserProfileEntryIndex INTEGER,
                       snmpUserProfileEntryContextName OCTET STRING,
                       snmpUserProfileEntryAuthProt INTEGER,
                       snmpUserProfileEntryPrivProt INTEGER,
                       snmpUserProfileEntryPrivPassword OCTET STRING,
                       snmpUserProfileEntryViewType INTEGER,
                       snmpUserProfileEntryIpAddress OCTET STRING
                       }


          snmpUserProfileEntryIndex   OBJECT-TYPE
                                    SYNTAX  INTEGER(0..255)
                                    MAX-ACCESS  read-only
                                    STATUS  current -- was mandatory
                                    DESCRIPTION
                                    "Index for SNMPv3 Agent User Profile entry."
                                    ::= { snmpUserProfileEntry 1 }

          snmpUserProfileEntryContextName  OBJECT-TYPE
                                    SYNTAX  OCTET STRING (SIZE(0..31))
                                    MAX-ACCESS  read-write
                                    STATUS  current -- was mandatory
                                    DESCRIPTION
                                    "SNMPv3 User Profile entry - Context name 
                                    for users to access MIB objects.  Note that context names can be duplicates   
                                    and can be shared among users.  Empty context names are allowed.  The 
                                    default context name is the empty string."                                   
                                    ::= { snmpUserProfileEntry 3 }
          
          snmpUserProfileEntryAuthProt   OBJECT-TYPE
                                    SYNTAX  INTEGER {
                                    none (1),
                                    md5 (2), 
                                    sha (3)
                                    }
                                    MAX-ACCESS  read-write
                                    STATUS  current -- was mandatory
                                    DESCRIPTION
                                    "SNMPv3 User Profile entry - Authentication Protocol 
                                    supported by the user."
                                    ::= { snmpUserProfileEntry 4 }
                                    
            snmpUserProfileEntryPrivProt   OBJECT-TYPE
                                    SYNTAX  INTEGER {
                                    none (1),
                                    des (2),
                                    aes (4)
                                    }
                                    MAX-ACCESS  read-write
                                    STATUS  current -- was mandatory
                                    DESCRIPTION
                                    "SNMPv3 User Profile entry - Privacy Protocol 
                                    supported by the user. The Privacy Password must be set
                                    and the Authentication Protocol must be md5 or sha
                                    before this field may be set to des or aes."
                                    ::= { snmpUserProfileEntry 6 }
                                    
           snmpUserProfileEntryPrivPassword  OBJECT-TYPE
                                    SYNTAX  OCTET STRING (SIZE(0..31))
                                    MAX-ACCESS  read-write
                                    STATUS  current -- was mandatory
                                    DESCRIPTION
                                    "SNMPv3 User Profile entry - Privacy password 
                                    for the user.
                                    
                                    NOTE: Value returned for the GET command is 
                                    meaningless for this MIB object for security reason."
                                    ::= { snmpUserProfileEntry 7 }

            snmpUserProfileEntryViewType   OBJECT-TYPE
                                    SYNTAX  INTEGER {
                                    read-Traps(1),
                                    read-Write-Traps(2),
                                    traps-Only(3)
                                    }
                                    MAX-ACCESS  read-write
                                    STATUS  current -- was mandatory
                                    DESCRIPTION
                                    "SNMPv3 User Profile entry - Access level (Get, Set, and 
                                    Traps) of the user. "
                                    ::= { snmpUserProfileEntry 8 }
                                    

           snmpUserProfileEntryIpAddress  OBJECT-TYPE
                                    SYNTAX  OCTET STRING (SIZE(0..63))
                                    MAX-ACCESS  read-write
                                    STATUS  current -- was mandatory
                                    DESCRIPTION
                                    "SNMPv3 User Profile entry - IP address or host name.
                                    Can either be a dotted decimal IP string (e.g. 9.37.44.2)
                                    or if DNS is enabled a host name."
                                    ::= { snmpUserProfileEntry 9 }
        
        -- ********************************************************************************
        -- DNS Configuration
        -- ********************************************************************************
        dnsConfig  OBJECT IDENTIFIER ::= { tcpProtocols 2 }

         dnsEnabled   OBJECT-TYPE
                      SYNTAX  INTEGER {
                        dnsDisabled(0),
                        dnsEnabled(1)
                      }
                      MAX-ACCESS  read-write
                      STATUS  current -- was mandatory
                      DESCRIPTION
                      "Disable or enable the DNS agent.

                      NOTE: To alter any of the configuration settings for the DNS agent,
                      the following procedure should be used:
                      (1) This object should be set to 'disabled'
                      (2) Make the modifications to other settings
                      (3) This object should be set to 'enabled'
                      (4) Restart the management module

                      Also note that when attempting to enable this agent, it is verified
                      that there is at least one valid DNS server IP address.  If this
                      verification fails, an error response will be returned and the DNS
                      agent will be left disabled."
                      ::= { dnsConfig 1 }

         dnsServerIPAddress1   OBJECT-TYPE
                      SYNTAX  IpAddress
                      MAX-ACCESS  read-write
                      STATUS  current -- was mandatory
                      DESCRIPTION
                      "Contains the primary DNS server IP address."
                      ::= { dnsConfig 2 }

         dnsServerIPAddress2   OBJECT-TYPE
                      SYNTAX  IpAddress
                      MAX-ACCESS  read-write
                      STATUS  current -- was mandatory
                      DESCRIPTION
                      "Contains the secondary DNS server IP address."
                      ::= { dnsConfig 3 }

         dnsServerIPAddress3   OBJECT-TYPE
                      SYNTAX  IpAddress
                      MAX-ACCESS  read-write
                      STATUS  current -- was mandatory
                      DESCRIPTION
                      "Contains the tertiary DNS server IP address."
                      ::= { dnsConfig 4 }


        -- ********************************************************************************
        -- SMTP Configuration
        -- ********************************************************************************
        smtpConfig  OBJECT IDENTIFIER ::= { tcpProtocols 3 }


         smtpServerNameOrIPAddress     OBJECT-TYPE
                      SYNTAX  OCTET STRING (SIZE(0..64))
                      MAX-ACCESS  read-write
                      STATUS  current -- was mandatory
                      DESCRIPTION
                      "A NULL terminated 64 byte string that contains the
                      SMTP server host name or IP address (a.b.c.d)."
                      ::= { smtpConfig 1 }

         attachmentsToEmailAlerts  OBJECT-TYPE
                      SYNTAX  INTEGER {
                        noAttachments(0),
                        attachServiceInformation(1)
                      }
                      MAX-ACCESS  read-write
                      STATUS  current -- was mandatory
                      DESCRIPTION
                      "Indicates if the service information should be attached to
                      an email alert."
                      ::= { smtpConfig 2 }


        tcpApplicationConfig  OBJECT IDENTIFIER ::= { tcpProtocols 4 }
         telnetInactivityTimeout  OBJECT-TYPE
                      SYNTAX  INTEGER
                      MAX-ACCESS  read-write
                      STATUS  current -- was mandatory
                      DESCRIPTION
                      "Default is 120 seconds. Value of zero is no timeout.
                      Max value is any positive 4 bytes value. Note that SSH also uses this 
                      timeout value to wait before disconnecting inactive SSH connections."
                      ::= { tcpApplicationConfig 1 }

         commandModeInactivityTimeout  OBJECT-TYPE
                      SYNTAX  INTEGER
                      MAX-ACCESS  read-write
                      STATUS  current -- was mandatory
                      DESCRIPTION
                      "The amount of time in seconds before the (Secure)TCP Command Mode times out.
                      Default value of 0 means no timeout. Max value is any positive 4 byte value."
                      ::= { tcpApplicationConfig 2 }

          secureCommandModeEnable   OBJECT-TYPE
                      SYNTAX  INTEGER
                      MAX-ACCESS  read-write
                      STATUS  current -- was mandatory
                      DESCRIPTION
                      "Set Secure TCP Command Mode number of connections.
                      AMM will provide a max of 20 connections for both Secure TCP Command Mode and TCP Command Mode.
                      A value of 0 means disabled.
                      If no valid server certificate is in place, Secure TCP Command Mode will not be allowed to set to enable.

                      NOTE: System Management Software requires this to be enabled for secure communication to the AMM."
                      ::= { tcpApplicationConfig 3 }

         commandModeEnable  OBJECT-TYPE
                      SYNTAX  INTEGER
                      MAX-ACCESS  read-write
                      STATUS  current -- was mandatory
                      DESCRIPTION
                      "Set TCP Command Mode number of connections.
                      AMM will provide a max of 20 connections for both Secure TCP Command Mode and TCP Command Mode.
                      A value of 0 means disabled.
                      NOTE: System Management Software requires this to be enabled for non-secure communication to the AMM."
                      ::= { tcpApplicationConfig 4 }
        
         slpAddrType  OBJECT-TYPE
                      SYNTAX  INTEGER {
                        multicast(0),
                        broadcast(1)
                      }
                      MAX-ACCESS  read-write
                      STATUS  current -- was mandatory
                      DESCRIPTION
                      "Set SLP address type to 0 (multicast) or 1 (broadcast). Note that when
                      slpAddrType is set to broadcast value then the multicast address set in
                      slpMulticastAddr will be ignored."
                      ::= { tcpApplicationConfig 5 }

         slpMulticastAddr  OBJECT-TYPE
                      SYNTAX  IpAddress
                      MAX-ACCESS  read-write
                      STATUS  current -- was mandatory
                      DESCRIPTION
                      "Service Locator Protocol Multicast address"
                      ::= { tcpApplicationConfig 6 }

         slpEnable  OBJECT-TYPE
                      SYNTAX  INTEGER {
                        disabled(0),
                        enabled(1)
                      }
                      MAX-ACCESS  read-write
                      STATUS  current -- was mandatory
                      DESCRIPTION
                      "Disable/Enable Service Location Protocol.

                      NOTE: Change to Service Location Protocol will take 
                      effect after the next restart of the MM."
                      ::= { tcpApplicationConfig 7}

         telnetEnable  OBJECT-TYPE
                      SYNTAX  INTEGER {
                        disabled(0),
                        enabled(1)
                      }
                      MAX-ACCESS  read-write
                      STATUS  current -- was mandatory
                      DESCRIPTION
                      "Disable/Enable telnet.
                      NOTE: Change to telnet enable/disable will take effect immediately."
                      ::= { tcpApplicationConfig 9 }

         sshEnable  OBJECT-TYPE
                      SYNTAX  INTEGER {
                        disabled(0),
                        enabled(1)
                      }
                      MAX-ACCESS  read-write
                      STATUS  current -- was mandatory
                      DESCRIPTION
                      "Disable/Enable SSH."
                      ::= { tcpApplicationConfig 10 }


         sshVersion  OBJECT-TYPE
                      SYNTAX  INTEGER {
                        allVersions(0),      -- deprecated
                        version2Only(1)
                      }
                      MAX-ACCESS  read-write
                      STATUS  current -- was mandatory
                      DESCRIPTION
                      "When SSH is enabled, this object allows the user to
                       configure whether the SSH server accepts all versions
                       of client connections or whether it restricts the 
                       connectivity to the more secure version 2 only.
                       
                       NOTE: Only SSH version 2 is supported now."
                      ::= { tcpApplicationConfig 11 }


         sslServerEnable  OBJECT-TYPE
                      SYNTAX  INTEGER {
                        disabled(0),
                        enabled(1)
                      }
                      MAX-ACCESS  read-write
                      STATUS  current -- was mandatory
                      DESCRIPTION
                      "Disable/Enable SSL Server."
                      ::= { tcpApplicationConfig 15 }
        

         sslClientEnable  OBJECT-TYPE
                      SYNTAX  INTEGER {
                        disabled(0),
                        enabled(1)
                      }
                      MAX-ACCESS  read-write
                      STATUS  current -- was mandatory
                      DESCRIPTION
                      "Disable/Enable SSL Client.  If no valid client or server certificate is in place, 
                      SSL client will not be allowed to set to enable."
                      ::= { tcpApplicationConfig 16 }
        

         ftpEnable    OBJECT-TYPE
                      SYNTAX  INTEGER {
                        disabled(0),
                        enabled(1)
                      }
                      MAX-ACCESS  read-write
                      STATUS  current -- was mandatory
                      DESCRIPTION
                      "Disable/Enable FTP."
                      ::= { tcpApplicationConfig 17 }
                                           

         tftpEnable   OBJECT-TYPE
                      SYNTAX  INTEGER {
                        disabled(0),
                        enabled(1)
                      }
                      MAX-ACCESS  read-write
                      STATUS  current -- was mandatory
                      DESCRIPTION
                      "Disable/Enable TFTP."
                      ::= { tcpApplicationConfig 19 }
                      

         smashTelnetEnable    OBJECT-TYPE
                      SYNTAX  INTEGER {
                        disabled(0),
                        enabled(1)
                      }
                      MAX-ACCESS  read-write
                      STATUS  current -- was mandatory
                      DESCRIPTION
                      "Disable/Enable SMASH CLP (System Management Architecture for 
                      Server Hardware Command Line Protocol) over Telnet.
                      This option is not available on all systems."
                      ::= { tcpApplicationConfig 20 }
                      

         smashSshEnable    OBJECT-TYPE
                      SYNTAX  INTEGER {
                        disabled(0),
                        enabled(1)
                      }
                      MAX-ACCESS  read-write
                      STATUS  current -- was mandatory
                      DESCRIPTION
                      "Disable/Enable SMASH CLP (System Management Architecture for 
                      Server Hardware Command Line Protocol) over SSH. A valid SSH 
                      server key must be installed before enabling secure SMASH. 
                      This option is not available on all systems."
                      ::= { tcpApplicationConfig 21 }
                      

         tftpCreateEmptyFile    OBJECT-TYPE
                      SYNTAX  OCTET STRING
                      MAX-ACCESS  read-write
                      STATUS  deprecated
                      DESCRIPTION
                      "This MIB object is no longer a requirement for TFTP and has been deprecated."
                      ::= { tcpApplicationConfig 22 }

         ftpTimeout   OBJECT-TYPE
                      SYNTAX  INTEGER
                      MAX-ACCESS  read-write
                      STATUS  current -- was mandatory
                      DESCRIPTION
                      "The amount of time before FTP times out.  Default is 300 seconds. 
                      Value of zero is no timeout. Max value is any positive 4 byte value."
                      ::= { tcpApplicationConfig 23 }

         rdEnable  OBJECT-TYPE
                      SYNTAX  INTEGER {
                        disabled(0),
                        enabled(1)
                      }
                      MAX-ACCESS  read-write
                      STATUS  current -- was mandatory
                      DESCRIPTION
                      "Disable/Enable Remote Disk.

                      NOTE: Change to Remote Disk will take effect after the 
                      next restart of the MM."
                      ::= { tcpApplicationConfig 24 }
        
         rdocEnable  OBJECT-TYPE
                      SYNTAX  INTEGER {
                        disabled(0),
                        enabled(1)
                      }
                      MAX-ACCESS  read-write
                      STATUS  current -- was mandatory
                      DESCRIPTION
                      "Disable/Enable Remote Disk on Card.

                      NOTE: Change to Remote Disk on Card will take effect 
                      after the next restart of the MM."
                      ::= { tcpApplicationConfig 25 }

        kvmEnable  OBJECT-TYPE
                      SYNTAX  INTEGER {
                        disabled(0),
                        enabled(1)
                      }
                      MAX-ACCESS  read-write
                      STATUS  current -- was mandatory
                      DESCRIPTION
                      "Disable/Enable KVM.

                      NOTE: Change to KVM will take effect after the next 
                      restart of the MM."
                      ::= { tcpApplicationConfig 26 }
                      
        -- The SSH Server Configuration Group
        mmSshServerConfig OBJECT IDENTIFIER ::= { tcpApplicationConfig 27 }
        
         mmSshServerHostKeyTable OBJECT-TYPE
                        SYNTAX  SEQUENCE OF MmSshServerHostKeyEntry
                        MAX-ACCESS  not-accessible
                        STATUS  current -- was mandatory
                        DESCRIPTION
                        "A table that contains per public/private host key
                        pair information."
                        ::= { mmSshServerConfig 1 }

         mmSshServerHostKeyEntry OBJECT-TYPE
                        SYNTAX  MmSshServerHostKeyEntry
                        MAX-ACCESS  not-accessible
                        STATUS  current -- was mandatory
                        DESCRIPTION
                        "A list of information about a particular public/private
                        host key pair."
                        INDEX { mmSshServerHostKeyIndex }
                        ::= { mmSshServerHostKeyTable 1 }

         MmSshServerHostKeyEntry ::= SEQUENCE {
                        mmSshServerHostKeyIndex  INTEGER,
                        mmSshServerHostKeyType  INTEGER,
                        mmSshServerHostKeySize  INTEGER,
                        mmSshServerHostKeyFingerprint  OCTET STRING
                        }

         mmSshServerHostKeyIndex  OBJECT-TYPE
                        SYNTAX  Integer32 (0..2147483647) -- was INTEGER
                        MAX-ACCESS  read-only
                        STATUS  current -- was mandatory
                        DESCRIPTION
                        "The index of the public/private host key pair."
                        ::= { mmSshServerHostKeyEntry 1 }

         mmSshServerHostKeyType  OBJECT-TYPE
                        SYNTAX  INTEGER { 
                            sshDss   (1), 
                            sshRsa   (2)
                        }
                        MAX-ACCESS  read-only
                        STATUS  current -- was mandatory
                        DESCRIPTION
                        "The type of the public/private host key pair."
                        ::= { mmSshServerHostKeyEntry 2 }

         mmSshServerHostKeySize  OBJECT-TYPE
                        SYNTAX  INTEGER { 
                             bits512   (1), 
                             bits768   (2),
                             bits1024  (3),
                             bits2048  (4),
                             bits4096  (5)
                        }
                        MAX-ACCESS  read-only
                        STATUS  current -- was mandatory
                        DESCRIPTION
                        "The size of the public/private host key pair.

                        NOTE: The AMM supports only the bits2048 value."
                        ::= { mmSshServerHostKeyEntry 3 }

         mmSshServerHostKeyFingerprint  OBJECT-TYPE
                        SYNTAX  OCTET STRING
                        MAX-ACCESS  read-only
                        STATUS  current -- was mandatory
                        DESCRIPTION
                        "The RSA fingerprint of the public part of the host key
                        pair.  This value can be used with the SSH client to
                        verify, on the initial connection, that the Secure Shell
                        server responding to the request is the server running
                        on the AMM. "
                        ::= { mmSshServerHostKeyEntry 4 }

         mmSshServerHostKeyGenerate OBJECT-TYPE
                        SYNTAX  INTEGER {
                        execute(1)
                        }
                        MAX-ACCESS  read-write
                        STATUS  current -- was mandatory
                        DESCRIPTION
                        "Initiate the new Host Keys generation process for the 
                        AMM SSH Server.
                        
                        NOTE: Value returned for the GET command is meaningless 
                        for this MIB object."
                        ::= { mmSshServerConfig 2 }
                        
         mmSshServerHostKeyGenerateProgress OBJECT-TYPE
                        SYNTAX  OCTET STRING
                        MAX-ACCESS  read-only
                        STATUS  current -- was mandatory
                        DESCRIPTION
                        "Indicate the progress of the key generation process."
                        ::= { mmSshServerConfig 3 }
                        
        -- TCP Port Assignment
        tcpPortAssignmentCfg    OBJECT IDENTIFIER ::= { tcpProtocols 5 } 
     
         tcpPortsRestoreDefault   OBJECT-TYPE
                      SYNTAX  INTEGER  {
                        execute(1)
                      }  
                      MAX-ACCESS  read-write
                      STATUS  current -- was mandatory
                      DESCRIPTION
                      "Reset all ports to default value.
                         http: 80
                         https: 443
                         telnet: 23
                         ssh: 22
                         SNMP agent: 161
                         SNMP trap: 162
                         TCP Command Mode: 6090
                         Secure TCP Command Mode: 6091
                         Remote Disk: 1044
                         Remote Disk-on-Card: 1045
                         Remote KVM: 3900
                         FTP: 21
                         FTP Data: 20
                         TFTP: 69
                         SMASH telnet: 50023 
                         SMASH ssh: 50022
                         SLP: 427
                         Storage Description Service: 1046

                      NOTE: Value returned for the GET command is meaningless for this MIB object."
                      ::= { tcpPortAssignmentCfg 1 }
                   
         httpPortAssignment   OBJECT-TYPE
                      SYNTAX  INTEGER 
                      MAX-ACCESS  read-write
                      STATUS  current -- was mandatory
                      DESCRIPTION
                      "HTTP port number. Default value is 80. Once changed, the URL's have to 
                      include :port at the end."
                      ::= { tcpPortAssignmentCfg 2 }
                   
         httpsPortAssignment   OBJECT-TYPE
                      SYNTAX  INTEGER 
                      MAX-ACCESS  read-write
                      STATUS  current -- was mandatory
                      DESCRIPTION
                      "SSL port number. Default value is 443. Once changed, the URL's have to 
                      include :port at the end."
                      ::= { tcpPortAssignmentCfg 3 }
                   
         telnetPortAssignment   OBJECT-TYPE
                      SYNTAX  INTEGER 
                      MAX-ACCESS  read-write
                      STATUS  current -- was mandatory
                      DESCRIPTION
                      "Telnet port number. Default value is 23. Port change will take effect immediately."
                      ::= { tcpPortAssignmentCfg 4 }
                   
         sshPortAssignment   OBJECT-TYPE
                      SYNTAX  INTEGER 
                      MAX-ACCESS  read-write
                      STATUS  current -- was mandatory
                      DESCRIPTION
                      "SSH port number. Default value is 22."
                      ::= { tcpPortAssignmentCfg 5 }
                   
         snmpAgentPortAssignment   OBJECT-TYPE
                      SYNTAX  INTEGER 
                      MAX-ACCESS  read-write
                      STATUS  current -- was mandatory
                      DESCRIPTION
                      "SNMP Agent port number. Default value is 161. MM has to be reset for change 
                      to take effect."
                      ::= { tcpPortAssignmentCfg 6 }
                   
         snmpTrapsPortAssignment   OBJECT-TYPE
                      SYNTAX  INTEGER 
                      MAX-ACCESS  read-write
                      STATUS  current -- was mandatory
                      DESCRIPTION
                      "SNMP Traps port number. Default value is 162. MM has to be reset for change 
                      to take effect."
                      ::= { tcpPortAssignmentCfg 7 }

        commandModePortAssignment    OBJECT-TYPE
                      SYNTAX  INTEGER 
                      MAX-ACCESS  read-write
                      STATUS  current -- was mandatory
                      DESCRIPTION
                      "TCP Command Mode port number. Default value is 6090. Change will take effect immediately."
                      ::= { tcpPortAssignmentCfg 8 }

        secureCommandModePortAssignment    OBJECT-TYPE
                      SYNTAX  INTEGER 
                      MAX-ACCESS  read-write
                      STATUS  current -- was mandatory
                      DESCRIPTION
                      "Secure TCP Command Mode port number. Default value is 6091. Change will take effect immediately."
                      ::= { tcpPortAssignmentCfg 9 }
                   
         rdPortAssignment   OBJECT-TYPE
                      SYNTAX  INTEGER 
                      MAX-ACCESS  read-write
                      STATUS  deprecated
                      DESCRIPTION
                      "Remote Disk port number. Default value is 1044. MM has to be reset for change 
                      to take effect.
                      NOTE: This mib object is deprecated and has been replaced by the rpPortAssignment object. 
                      Attempts to set the port value for this SNMP object are no longer supported and any
                      read of the value associated with this object will return the rpPortAssignment
                      (Remote Presence) port information."
                      ::= { tcpPortAssignmentCfg 10 }

         rdocPortAssignment   OBJECT-TYPE
                      SYNTAX  INTEGER 
                      MAX-ACCESS  read-write
                      STATUS  deprecated
                      DESCRIPTION
                      "Remote Disk-on-Card port number. Default value is 1045. MM has to be reset for
                      change to take effect.
                      NOTE: This mib object is deprecated and has been replaced by the rpPortAssignment object. 
                      Attempts to set the port value for this SNMP object are no longer supported and any
                      read of the value associated with this object will return the rpPortAssignment
                      (Remote Presence) port information."
                      ::= { tcpPortAssignmentCfg 11 }

         kvmPortAssignment   OBJECT-TYPE
                      SYNTAX  INTEGER 
                      MAX-ACCESS  read-write
                      STATUS  deprecated
                      DESCRIPTION
                      "Remote KVM port number. Default value is 3900. MM has to be reset for
                      change to take effect.
                      NOTE: This mib object is deprecated and has been replaced by the rpPortAssignment object. 
                      Attempts to set the port value for this SNMP object are no longer supported and any
                      read of the value associated with this object will return the rpPortAssignment
                      (Remote Presence) port information."
                      ::= { tcpPortAssignmentCfg 12 }

         ftpPortAssignment   OBJECT-TYPE
                      SYNTAX  INTEGER 
                      MAX-ACCESS  read-write
                      STATUS  current -- was mandatory
                      DESCRIPTION
                      "FTP port number. Default value is 21. MM has to be reset for change 
                      to take effect."
                      ::= { tcpPortAssignmentCfg 13 }
        
         ftpDataPortAssignment   OBJECT-TYPE
                      SYNTAX  INTEGER 
                      MAX-ACCESS  read-write
                      STATUS  current -- was mandatory
                      DESCRIPTION
                      "FTP Data port number. Default value is 20. MM has to be reset for change 
                      to take effect."
                      ::= { tcpPortAssignmentCfg 14 }
        
         tftpPortAssignment   OBJECT-TYPE
                      SYNTAX  INTEGER 
                      MAX-ACCESS  read-write
                      STATUS  current -- was mandatory
                      DESCRIPTION
                      "TFTP port number. Default value is 69. MM has to be reset for change 
                      to take effect."
                      ::= { tcpPortAssignmentCfg 15 }
        
         smashTelnetPortAssignment   OBJECT-TYPE
                      SYNTAX  INTEGER 
                      MAX-ACCESS  read-write
                      STATUS  current -- was mandatory
                      DESCRIPTION
                      "The port number for SMASH CLP (System Management Architecture for Server 
                      Hardware Command Line Protocol) over telnet. Default value is 50023. 
                      Change will take effect immediately.  
                      This option is not available on all systems."
                      ::= { tcpPortAssignmentCfg 17 }
        
         smashSshPortAssignment   OBJECT-TYPE
                      SYNTAX  INTEGER 
                      MAX-ACCESS  read-write
                      STATUS  current -- was mandatory
                      DESCRIPTION
                      "The port number for SMASH CLP (System Management Architecture for Server 
                      Hardware Command Line Protocol) over SSH. Default value is 50022.  
                      This option is not available on all systems."
                      ::= { tcpPortAssignmentCfg 18 }

         slpPortAssignment   OBJECT-TYPE
                      SYNTAX  INTEGER 
                      MAX-ACCESS  read-write
                      STATUS  current -- was mandatory
                      DESCRIPTION
                      "Service Location Protocol port number. Default value is 427. MM has to be reset for change 
                      to take effect.
                      NOTE: This value is normally required to be 427 to interoperate properly
                      with other SLP enabled applications."
                      ::= { tcpPortAssignmentCfg 19 }
        
         sdsPortAssignment   OBJECT-TYPE
                      SYNTAX  INTEGER 
                      MAX-ACCESS  read-write
                      STATUS  deprecated
                      DESCRIPTION
                      "Storage description service port number. Default value is 1046. MM has to be reset for 
                      change to take effect.
                      NOTE: This mib object is deprecated and has been replaced by the rpPortAssignment object. 
                      Attempts to set the port value for this SNMP object are no longer supported and any
                      read of the value associated with this object will return the rpPortAssignment
                      (Remote Presence) port information."
                      ::= { tcpPortAssignmentCfg 20 }
                      
        rpPortAssignment   OBJECT-TYPE
                      SYNTAX  INTEGER 
                      MAX-ACCESS  read-write
                      STATUS  current -- was mandatory
                      DESCRIPTION
                      "Remote Presence port. Default value is 3900. This port cannot be disabled since it is
                      the single service entry point for all the services provided by AMM RPServ to clients."
                      ::= { tcpPortAssignmentCfg 21 }
                
        
        -- LDAP Client Configuration
        ldapClientCfg    OBJECT IDENTIFIER ::= { tcpProtocols 6 } 
        
         ldapServer1NameOrIPAddress     OBJECT-TYPE
                      SYNTAX  OCTET STRING (SIZE(0..64))
                      MAX-ACCESS  read-write
                      STATUS  current -- was mandatory
                      DESCRIPTION
                      "A NULL terminated 64 byte string that contains the
                      LDAP server host name or IP address (a.b.c.d)."
                      ::= { ldapClientCfg 1 }

         ldapServer1PortNumber   OBJECT-TYPE
                      SYNTAX  INTEGER 
                      MAX-ACCESS  read-write
                      STATUS  current -- was mandatory
                      DESCRIPTION
                      "LDAP server port number."
                      ::= { ldapClientCfg 2 }
                   
         ldapServer2NameOrIPAddress     OBJECT-TYPE
                      SYNTAX  OCTET STRING (SIZE(0..64))
                      MAX-ACCESS  read-write
                      STATUS  current -- was mandatory
                      DESCRIPTION
                      "A NULL terminated 64 byte string that contains the
                      LDAP server host name or IP address (a.b.c.d)."
                      ::= { ldapClientCfg 3 }

         ldapServer2PortNumber   OBJECT-TYPE
                      SYNTAX  INTEGER 
                      MAX-ACCESS  read-write
                      STATUS  current -- was mandatory
                      DESCRIPTION
                      "LDAP server port number."
                      ::= { ldapClientCfg 4 }
                   
         ldapServer3NameOrIPAddress     OBJECT-TYPE
                      SYNTAX  OCTET STRING (SIZE(0..64))
                      MAX-ACCESS  read-write
                      STATUS  current -- was mandatory
                      DESCRIPTION
                      "A NULL terminated 64 byte string that contains the
                      LDAP server host name or IP address (a.b.c.d)."
                      ::= { ldapClientCfg 5 }

         ldapServer3PortNumber   OBJECT-TYPE
                      SYNTAX  INTEGER 
                      MAX-ACCESS  read-write
                      STATUS  current -- was mandatory
                      DESCRIPTION
                      "LDAP server port number."
                      ::= { ldapClientCfg 6 }
                   
         ldapRootDN     OBJECT-TYPE
                      SYNTAX  OCTET STRING (SIZE(0..64))
                      MAX-ACCESS  read-write
                      STATUS  current -- was mandatory
                      DESCRIPTION
                      "Distinguished Name for root entry of directory tree. 
                      An example might look like dn=foobar,dn=com."
                      ::= { ldapClientCfg 7 }

         ldapUserSearchBaseDN     OBJECT-TYPE
                      SYNTAX  OCTET STRING (SIZE(0..64))
                      MAX-ACCESS  read-write
                      STATUS  current -- was mandatory
                      DESCRIPTION
                      "As part of the user authentication process, it is necessary to search 
                      the LDAP server for one or more attributes associated with a particular 
                      user. Any search request must specify the base DN for the actual search. 
                      This field specifies the base DN which should be used to search the User 
                      directory. An example might look like cn=users,dn=foobar,dn=com. If this 
                      field is left blank, the Root DN will be used as the search base instead.
                      As mentioned, user searches are part of the authentication process. They 
                      are carried out to retrieve information about the user such as login 
                      permissions, callback number, and group memberships. For Version 2.0 LDAP 
                      clients, it is strongly encouraged that this parameter be configured, 
                      otherwise a search using the root DN may not succeed (as seen on Active 
                      Directory servers).
                      
                      NOTE: This MIB object is for MM only."
                      ::= { ldapClientCfg 8 }

         ldapGroupFilter     OBJECT-TYPE
                      SYNTAX  OCTET STRING (SIZE(0..64))
                      MAX-ACCESS  read-write
                      STATUS  current -- was mandatory
                      DESCRIPTION
                      "This filter is used for group authentication. It specifies what group or 
                      groups that this MM belongs to. If left blank, group authentication is 
                      disabled. Otherwise, group authentication will be performed against the 
                      filter. The filter can be a specific group name (e.g. RSAWest), a wildcard (*) 
                      which matches everything, or a wildcard with a prefix (e.g. RSA*). The default 
                      filter is RSA*. 
                      After user authentication, group authentication will take place, whereby an 
                      attempt will be made to match the group or groups (that the user belongs to) 
                      to the group filter defined here. If there is no match, the user will not pass 
                      authentication and will be blocked. If there is a match, the login permissions 
                      for the user will be retrieved from the matched group(s), unless the user 
                      already has login permissions assigned directly from the user record retrieved 
                      from the LDAP server."
                      ::= { ldapClientCfg 9 }

         ldapBindingMethod  OBJECT-TYPE
                      SYNTAX  INTEGER {
                        anonymousAuthentication(0),
                        clientAuthentication(1),
                        userPrincipalName(2),
                        strictUserPrincipalName(3)
                      }
                      MAX-ACCESS  read-write
                      STATUS  current -- was mandatory
                      DESCRIPTION
                      "On initial binds to the LDAP server during user authentication, there are 
                      three options:
                      Anonymous authentication: Bind attempt is made without a client DN or password. 
                      If the bind is successful, a search will be requested in order to find an entry 
                      on the LDAP server for the user attempting to login. If an entry is found, a 
                      second attempt to bind will be attempted, this time with the user's DN and 
                      password. If this succeeds, the user is deemed to have passed the user 
                      authentication phase. Group authentication is then attempted if it is enabled.
                      Client authentication: Bind attempt is made with client DN and password 
                      specified by this configuration parameter. If the bind is successful, we 
                      proceed as above.
                      User Principal Name (UPN): Bind attempt is made directly with the credentials 
                      used during the login process. If this succeeds, the user is deemed to have 
                      passed the user authentication phase. Note that for Active Directory servers, 
                      the userid can have the form someuser@somedomain or simply someuser.
                      Strict UPN: This is the same as UPN above, except that the userid must have 
                      the form someuser@somedomain. The string entered by the user will be parsed 
                      for the @ symbol.
                      
                      NOTE: strictUserPrincipalName(3) option is available on MM only."
                      ::= { ldapClientCfg 10 }

         ldapClientAuthenticationDN     OBJECT-TYPE
                      SYNTAX  OCTET STRING (SIZE(0..64))
                      MAX-ACCESS  read-write
                      STATUS  current -- was mandatory
                      DESCRIPTION
                      "The initial bind to the LDAP server during user authentication can be 
                      performed with anonymous authentication, client based authentication, or UPN. 
                      The client based option requires a client DN and password as parameters to 
                      the bind request. These parameters are configured here. Note that the password 
                      can be left blank."
                      ::= { ldapClientCfg 11 }

         ldapClientAuthenticationPassword     OBJECT-TYPE
                      SYNTAX  OCTET STRING (SIZE(0..16))
                      MAX-ACCESS  read-write
                      STATUS  current -- was mandatory
                      DESCRIPTION
                      "The client authentication password"
                      ::= { ldapClientCfg 12 }

         ldapUIDsearchAttribute     OBJECT-TYPE
                      SYNTAX  OCTET STRING (SIZE(0..64))
                      MAX-ACCESS  read-write
                      STATUS  current -- was mandatory
                      DESCRIPTION
                      "When the binding method selected is Anonymous authentication or Client 
                      authentication, the initial bind to the LDAP server is followed by a search 
                      request aimed at retrieving specific information about the user, including the 
                      user's DN, login permissions, and group ownerships. In order to retrieve this 
                      information, the search request must specify the attribute name used to 
                      represent userids on that server. Specifically, this name is used as a search 
                      filter against the login id entered by the user. This attribute name is 
                      configured here. If this field is left blank, a default of uid is used during 
                      user authentication. 
                      For example, on Active Directory servers, the attribute name used for userids 
                      is often sAMAccoutName. 
                      When the binding method selected is UPN or Strict UPN, this field defaults 
                      automatically to userPrincipalName during user authentication if the userid 
                      entered has the form userid@somedomain."
                      ::= { ldapClientCfg 13 }

         ldapGroupSearchAttribute     OBJECT-TYPE
                      SYNTAX  OCTET STRING (SIZE(0..64))
                      MAX-ACCESS  read-write
                      STATUS  current -- was mandatory
                      DESCRIPTION
                      "When the MM Group Filter name is configured, it is necessary to retrieve 
                      from the LDAP server the list of groups that a particular user belongs to. 
                      This is required to do group authentication. In order to retrieve this list, 
                      the search filter sent to the server must specify the attribute name associated 
                      with groups. This field specifies this attribute name. 
                      If this field is left blank, the attribute name in the filter will default 
                      to memberOf."
                      ::= { ldapClientCfg 14 }

         ldapLoginPermissionAttribute     OBJECT-TYPE
                      SYNTAX  OCTET STRING (SIZE(0..64))
                      MAX-ACCESS  read-write
                      STATUS  current -- was mandatory
                      DESCRIPTION
                      "When a user successfully authenticates via a LDAP server, it is necessary 
                      to retrieve the login permissions for this user. In order to retrieve these 
                      permissions, the search filter sent to the server must specify the attribute 
                      name associated with login permissions. This field specifies this attribute 
                      name."
                      ::= { ldapClientCfg 15 }

         ldapUseDNSOrPreConfiguredServers     OBJECT-TYPE
                      SYNTAX  INTEGER {
                        usePreConfiguredLDAPServers (0),
                        useDNSToFindLDAPServers (1)
                      }
                      MAX-ACCESS  read-write
                      STATUS  current -- was mandatory
                      DESCRIPTION
                      "The MM contains a Version 2.0 LDAP Client that may be configured to provide 
                      user authentication through one or more LDAP servers. The LDAP server(s) to be 
                      used for authentication can be discovered dynamically or manually pre-configured. 
                      
                      If the usePreConfiguredLDAPServers option is selected, up to 3 LDAP servers can 
                      be configured. Simply enter the server's IP address or hostname (assuming DNS 
                      is enabled).  The port number for each server is optional. If left blank, 
                      the default value of 389 is used for non-secured LDAP connections. For secured 
                      connections, the default is 636. At least one server must be configured.
                      
                      If the useDNSToFindLDAPServers is selected, the mechanisms described by RFC2782 
                      (A DNS RR for specifying the location of services) are applied to find the 
                      server(s). This is known as DNS SRV."
                      ::= { ldapClientCfg 16 }
         
         ldapDomainSource     OBJECT-TYPE
                      SYNTAX  INTEGER {
                        extractSearchDomainFromLoginID (0),
                        useOnlyConfiguredSearchDomainBelow (1),
                        tryLoginFirstThenConfiguredValue (2)
                      }
                      MAX-ACCESS  read-write
                      STATUS  current -- was mandatory
                      DESCRIPTION
                      "The DNS SRV request sent to the DNS server must specify a domain name. 
                      The LDAP client will determine where to get this domain name based on one 
                      of the following three options: 
                      
                        - extractSearchDomainFromLoginID: With this option, the LDAP client will 
                      use the domain name in the login id. For example, if the login id is 
                      joesmith@mycompany.com, the domain name equals mycompany.com. If the domain 
                      name cannot be extracted, the DNS SRV will fail, causing the user 
                      authentication to fail automatically.
                      
                        - useOnlyConfiguredSearchDomainBelow: With this option, the LDAP client 
                      will use the domain name configured in the Search Domain parameter. 
                      
                        - tryLoginFirstThenConfiguredValue: With this option, the LDAP client will 
                      first attempt to extract the domain name from the login id. If this succeeds, 
                      this domain name will be used in the DNS SRV request. If there is no domain 
                      name present in the login id, the LDAP client will instead use the configured 
                      Search Domain parameter as the domain name in the DNS SRV request. 
                      If nothing is configured, user authentication will fail immediately."
                      ::= { ldapClientCfg 17 }

         ldapSearchDomain     OBJECT-TYPE
                      SYNTAX  OCTET STRING (SIZE(0..64))  
                      MAX-ACCESS  read-write
                      STATUS  current -- was mandatory
                      DESCRIPTION
                      "This parameter may be used as the domain name in the DNS SRV request, 
                      depending on how the Domain Source parameter is configured."
                      ::= { ldapClientCfg 18 }

         ldapServiceName     OBJECT-TYPE
                      SYNTAX  OCTET STRING (SIZE(0..16))  
                      MAX-ACCESS  read-write
                      STATUS  current -- was mandatory
                      DESCRIPTION
                      "The DNS SRV request sent to the DNS server must also specify a service name. 
                      The configured value will be used for this purpose. If left blank, the default 
                      value used is 'ldap'. Note that the DNS SRV request must also specify a protocol 
                      name. This defaults to 'tcp' and is not configurable."
                      ::= { ldapClientCfg 19 }

         ldapRBSModelCfg     OBJECT-TYPE
                      SYNTAX  INTEGER {
                        oldPermissionString(0),
                        newRBSModel(1)
                      }
                      MAX-ACCESS  read-write
                      STATUS  current -- was mandatory
                      DESCRIPTION
                      "There are two mechanisms to authenticate and authorize users on the AMM when 
                      using an LDAP-enabled server. The first mechanism (oldPermissionString), also 
                      known as version 1, uses bitstrings to associate permissions to users and groups. 
                      Version1 supports Active Directory, Novell eDirectory, and OPenLDAP based 
                      servers.  The second mechanism (newRBSModel),  also known as version 2, 
                      uses a new Role-Based-Security (RBS) model. This mechanism is only available 
                      for Active Directory servers, and requires the use of a snap-in that runs on any 
                      windows platform. This snap-in tool allows you to configure roles on an Active 
                      Directory server of your choice, and to associate users/groups and AMMs to those 
                      roles. A role identifies the permissions given to users and groups associated with 
                      that role, and also identifies the targets (e.g. AMM) to which this role is attached. 
                      The use of bitstrings in version 2 disappears, making the configuration much more 
                      manageable and user-friendly. Note that if you are not using Active Directory, then 
                      you should not enable version 2. Also note that before enabling version 2, you should 
                      already have your roles configured on your Active Directory server. The old version 1
                      bitstring model cannot be automatically converted to the new version 2 model. This is 
                      why you must configure your users and groups before enabling version 2. Once 
                      enabled, the change takes effect immediately. The default value for this field is 
                      oldPermissionString."
                      ::= { ldapClientCfg 20 }
                      
                      
         ldapTargetName     OBJECT-TYPE
                      SYNTAX  OCTET STRING (SIZE(0..16))  
                      MAX-ACCESS  read-write
                      STATUS  current -- was mandatory
                      DESCRIPTION
                      "When administrator chooses Enhanced Role Based Security authentication model, 
                      he can associate  one AMM with one managed target object in Snap-in (one tool 
                      to configure LDAP users permission) via one target name. The AMM target name can 
                      be looked as alias of AMM, administrator can change it according to his 
                      configuration requirements. This is a string of up to 63 characters (plus the 
                      null character)"
                      ::= { ldapClientCfg 21 }
        -- ********************************************************************************
        -- Uplink Check Configuration
        -- ********************************************************************************

        uplinkCheckConfig  OBJECT IDENTIFIER ::= { tcpProtocols 7 }

         uplinkCheckEnabled   OBJECT-TYPE
                      SYNTAX  INTEGER {
                        uplinkCheckDisabled(0),
                        uplinkCheckEnabled(1)
                      }
                      MAX-ACCESS  read-write
                      STATUS  current -- was mandatory
                      DESCRIPTION
                      "Disable or enable network uplink checking for physical detection.
                      
                      NOTE: This MIB object is only applicable to systems with a standby MM."
                      ::= { uplinkCheckConfig 1 }

         uplinkCheckDelay   OBJECT-TYPE
                      SYNTAX  INTEGER 
                      MAX-ACCESS  read-write
                      STATUS  current -- was mandatory
                      DESCRIPTION
                      "Delay, in minutes (1-2880), between discovery of a failed network uplink and
                      the subsequent MM failover for physical detection.
                      
                      NOTE: This MIB object is only applicable to systems with a standby MM."
                      ::= { uplinkCheckConfig 2 }

         logicalUplinkDestination    OBJECT-TYPE
                      SYNTAX  IpAddress
                      MAX-ACCESS  read-write
                      STATUS  current -- was mandatory
                      DESCRIPTION
                      "Destination IP for MM to check its logical link.
                      Specify a non-zero IP Address in order to enable logical uplink checking.
                      
                      NOTE: This MIB object is only applicable to systems with a standby MM."
                      ::= { uplinkCheckConfig 3 }

         logicalUplinkCheckEnabled   OBJECT-TYPE
                      SYNTAX  INTEGER {
                        uplinkCheckDisabled(0),
                        uplinkCheckEnabled(1)
                      }
                      MAX-ACCESS  read-write
                      STATUS  current -- was mandatory
                      DESCRIPTION
                      "Disable or enable network uplink checking for logical detection.
                      logicalUplinkDestination must be set to a non-zero IP Address before enable 
                      logical uplink checking.
                      
                      NOTE: This MIB object is only applicable to systems with a standby MM."
                      ::= { uplinkCheckConfig 4 }

         logicalUplinkCheckDelay   OBJECT-TYPE
                      SYNTAX  INTEGER 
                      MAX-ACCESS  read-write
                      STATUS  current -- was mandatory
                      DESCRIPTION
                      "Delay, in minutes(1-2880), between discovery of a failed network uplink and
                      the subsequent MM failover for logical detection.
                      
                      NOTE: This MIB object is only applicable to systems with a standby MM."
                      ::= { uplinkCheckConfig 5 }


         physicalUplinkCheckDelayInSecs   OBJECT-TYPE
                      SYNTAX  INTEGER 
                      MAX-ACCESS  read-write
                      STATUS  current -- was mandatory
                      DESCRIPTION
                      "Delay, in seconds(10-172800), between discovery of a failed network uplink and
                      the subsequent MM failover for physical detection.
                      
                      NOTE: This MIB object is only applicable to systems with a standby MM."
                      ::= { uplinkCheckConfig 6 } 
                      

         logicalUplinkCheckDelayInSecs   OBJECT-TYPE
                      SYNTAX  INTEGER 
                      MAX-ACCESS  read-write
                      STATUS  current -- was mandatory
                      DESCRIPTION
                      "Delay, in seconds(60-172800), between discovery of a failed network uplink and
                      the subsequent MM failover for logical detection.
                      
                      NOTE: This MIB object is only applicable to systems with a standby MM."
                      ::= { uplinkCheckConfig 7 }


        -- ********************************************************************************
        -- NTP Configuration
        -- ********************************************************************************
        ntpConfig  OBJECT IDENTIFIER ::= { tcpProtocols 8 }
        
         ntpEnable    OBJECT-TYPE
                      SYNTAX  INTEGER {
                        disabled(0),
                        enabled(1)
                      }
                      MAX-ACCESS  read-write
                      STATUS  current -- was mandatory
                      DESCRIPTION
                      "Disable/Enable the NTP client.  The client will update
                      the AMM system clock at the frequency specified."
                      ::= { ntpConfig 1 }

         ntpIpAddressHostname  OBJECT-TYPE
                      SYNTAX  OCTET STRING (SIZE(0..63))
                      MAX-ACCESS  read-write
                      STATUS  current -- was mandatory
                      DESCRIPTION
                      "NTP server's IP address or hostname if DNS is enabled
                      and configured."
                      ::= { ntpConfig 2 }
                                    
         ntpUpdateFrequency  OBJECT-TYPE
                      SYNTAX  INTEGER
                      MAX-ACCESS  read-write
                      STATUS  current -- was mandatory
                      DESCRIPTION
                      "The frequency in minutes that the NTP service runs.
                      The value range is 0 to 45000. If the NTP update frequency 
                      is set to 0, the AMM clock can only be synchronized with the 
                      NTP server manually."
                      ::= { ntpConfig 3 }
                      
         ntpLastUpdate  OBJECT-TYPE
                      SYNTAX  OCTET STRING
                      MAX-ACCESS  read-only
                      STATUS  current -- was mandatory
                      DESCRIPTION
                      "The date and time that the NTP server last updated
                      the system clock."
                      ::= { ntpConfig 4 }
                      
         ntpUpdateClock  OBJECT-TYPE
                      SYNTAX  INTEGER  {
                        execute(1)
                      }  
                      MAX-ACCESS  read-write
                      STATUS  current -- was mandatory
                      DESCRIPTION
                      "Update the AMM system clock with the specified NTP server.
                      A valid NTP server must be configured first."
                      ::= { ntpConfig 5 }

         ntpAuthEntry  OBJECT-TYPE
                      SYNTAX  OCTET STRING
                      MAX-ACCESS  read-write
                      STATUS  current -- was mandatory
                      DESCRIPTION
                      "The NTP v3 authentication entry to be used for time sync
                      with a secure NTP server. The format of an authentication
                      entry is <key index> <key type> <key>. <key index> must
                      be an integer between 1 and 65535. <key type> must be
                      M. <key> is the actual value of the authentication
                      key as configured on the NTP server.
                      The GET command returns back data in the format:
                      <key index> <key type>
                      It does not return the actual key."
                      ::= { ntpConfig 6 }

         ntpAuthEnable  OBJECT-TYPE
                      SYNTAX  INTEGER {
                        disabled(0),
                        enabled(1)
                      }
                      MAX-ACCESS  read-write
                      STATUS  current -- was mandatory
                      DESCRIPTION
                      "Enables/Disables NTP v3 authentication"
                      ::= { ntpConfig 7 }
        -- ********************************************************************************
        -- SYSLOG Configuration
        -- ********************************************************************************
        syslogConfig  OBJECT IDENTIFIER ::= { tcpProtocols 9 }

        syslogSevFilterLevel  OBJECT-TYPE
                    SYNTAX  INTEGER {
                      error(0),
                      warning(1),
                      information(2)
                    }
                    MAX-ACCESS  read-write
                    STATUS  current -- was mandatory
                    DESCRIPTION
                    "syslogSevFilterLevel    error/warning/information ."
                    ::= { syslogConfig 1 }


         -- ********************************************************************************
         -- syslogCollector   Configuration
         -- ********************************************************************************
         syslogCollectorConfig  OBJECT IDENTIFIER ::= { syslogConfig 2 }



          -- ********************************************************************************
          -- Syslog Collector Configuration table
          -- ********************************************************************************

          syslogCollectorTable  OBJECT-TYPE
                                SYNTAX  SEQUENCE OF SyslogCollectorEntry
                                MAX-ACCESS  not-accessible
                                STATUS  current -- was mandatory
                                DESCRIPTION
                                "Table of Syslog Collector entries"
                                ::= {  syslogCollectorConfig 1 }

          syslogCollectorEntry  OBJECT-TYPE
                                SYNTAX  SyslogCollectorEntry
                                MAX-ACCESS  not-accessible
                                STATUS  current -- was mandatory
                                DESCRIPTION
                                "Syslog Collector entries"
                                INDEX { syslogCollectorIndex }
                                ::= { syslogCollectorTable 1 }


          SyslogCollectorEntry ::= SEQUENCE {
                       syslogCollectorIndex INTEGER,
                       syslogCollectorHostnameOrIpAddress OCTET STRING,
                       syslogCollectorPort INTEGER,
                       syslogCollectorEnable INTEGER
                       }

          syslogCollectorIndex   OBJECT-TYPE
                                    SYNTAX  INTEGER(0..255)
                                    MAX-ACCESS  read-only
                                    STATUS  current -- was mandatory
                                    DESCRIPTION
                                    "Index for Syslog Collector entry."
                                    ::= { syslogCollectorEntry 1 }

          syslogCollectorHostnameOrIpAddress  OBJECT-TYPE
                                    SYNTAX  OCTET STRING (SIZE(0..63))
                                    MAX-ACCESS  read-write
                                    STATUS  current -- was mandatory
                                    DESCRIPTION
                                    "Syslog Collector IP address or host name."
                                    ::= { syslogCollectorEntry 2 }

          syslogCollectorPort   OBJECT-TYPE
                                    SYNTAX  INTEGER(1..65535)
                                    MAX-ACCESS  read-write
                                    STATUS  current -- was mandatory
                                    DESCRIPTION
                                    "Syslog Collector port number."
                                    ::= { syslogCollectorEntry 3 }

          syslogCollectorEnable   OBJECT-TYPE
                                    SYNTAX  INTEGER {
                                      disabled(0),
                                      enabled(1)
                                    }
                                    MAX-ACCESS  read-write
                                    STATUS  current -- was mandatory
                                    DESCRIPTION
                                    "Syslog Collector enable/disable."
                                    ::= { syslogCollectorEntry 4 }
       -- ********************************************************************************
       -- SOL (Serial Over LAN) Configuration
       -- ********************************************************************************
       solConfiguration  OBJECT IDENTIFIER ::= { configureSP 10 }

        -- ********************************************************************************
        -- SOL Global Configuration
        -- ********************************************************************************
        solGlobalConfig  OBJECT IDENTIFIER ::= { solConfiguration 1 }

         solEnable  OBJECT-TYPE
                    SYNTAX  INTEGER {
                      solDisabled(0),
                      solEnabled(1)
                    }
                    MAX-ACCESS  read-write
                    STATUS  current -- was mandatory
                    DESCRIPTION
                    "Disable/Enable SOL dynamically."
                    ::= { solGlobalConfig 1 }

         solVlanId  OBJECT-TYPE
                    SYNTAX  INTEGER
                    MAX-ACCESS  read-write
                    STATUS  current -- was mandatory
                    DESCRIPTION
                    "This is the virtual LAN ID for the internal management network between the MM and 
                    the Blade System Management Processors (BSMPs).  The range of valid VLAN ID's 
                    is 3 to 4095."
                    ::= { solGlobalConfig 2 }

         solAccumulateTimeout  OBJECT-TYPE
                    SYNTAX  INTEGER
                    MAX-ACCESS  read-write
                    STATUS  current -- was mandatory
                    DESCRIPTION
                    "This value specifies how much time in millisecond SOL to buffer data before
                    sending the next SOL packet since the last SOL packet was transmitted.
                    Valid value from 5 ms to 1275 ms. The value is in 5 ms increment. Value
                    is not in 5 ms increment will be truncated to a nearest 5s. Default value
                    is 5 ms."
                    ::= { solGlobalConfig 3 }

         solCharSendThreshold  OBJECT-TYPE
                    SYNTAX  INTEGER
                    MAX-ACCESS  read-write
                    STATUS  current -- was mandatory
                    DESCRIPTION
                    "This value specifies how many characters SOL to buffer before
                    sending the next SOL packet since the last SOL packet was transmitted.
                    Valid value is from 1 to 255"
                    ::= { solGlobalConfig 4 }

         solRetry  OBJECT-TYPE
                    SYNTAX  INTEGER
                    MAX-ACCESS  read-write
                    STATUS  current -- was mandatory
                    DESCRIPTION
                    "Retry count. Valid value from 0-7. 0 means no retries after packet is transmitted.
                    Packet will be dropped if no ACK/NACK received by the time retries expired."
                    ::= { solGlobalConfig 5 }

         solRetryInterval  OBJECT-TYPE
                    SYNTAX  INTEGER
                    MAX-ACCESS  read-write
                    STATUS  current -- was mandatory
                    DESCRIPTION
                    "Retry Interval in 10 ms increment. Sets the time that the SOL will 
                    wait before the first retry and the time between retries when sending SOL 
                    packets to the remote blade. Value range is from 0 to 2550 ms in 10 ms
                    increment. 0 means retries will be sent back-to-back."
                    ::= { solGlobalConfig 6 }
                           
      solExitToCliKeySeq  OBJECT-TYPE
                    SYNTAX  OCTET STRING(SIZE(0..16))
                    MAX-ACCESS  read-write
                    STATUS  current -- was mandatory
                    DESCRIPTION
                    "This is the keystroke sequence used to escape out of SOL session and back to CLI 
                    console. This sequence must have at least one character. The caret symbol (^) 
                    has a special meaning in this sequence. It denotes 'Ctrl' for keystrokes that 
                    map to Ctrl sequences (for example, ^[ for the escape key and ^M for carriage 
                    return). All occurrences of ^ will be interpreted as part of a Ctrl sequence. 
                    Refer to an ASCII-to-key conversion table for a complete list of Ctrl sequences. 
                    The default value for this field is '^[(' i.e. ESC followed by (."
                    ::= { solGlobalConfig 7 }
                   
      solResetBladeKeySeq  OBJECT-TYPE
                    SYNTAX  OCTET STRING(SIZE(0..16))
                    MAX-ACCESS  read-write
                    STATUS  current -- was mandatory
                    DESCRIPTION
                    "This is the keystroke sequence used to reset the blade while in SOL session 
                    console. This sequence must have at least one character. The caret symbol (^) 
                    has a special meaning in this sequence. It denotes 'Ctrl' for keystrokes that 
                    map to Ctrl sequences (for example, ^[ for the escape key and ^M for carriage 
                    return). All occurrences of ^ will be interpreted as part of a Ctrl sequence. 
                    Refer to an ASCII-to-key conversion table for a complete list of Ctrl sequences. 
                    The default value for this field is '^[R^[r^[R' i.e. ESC R ESC r ESC R."
                    ::= { solGlobalConfig 8 }
                   

         --  Blade SOL config
         solBladeConfig  OBJECT IDENTIFIER ::= { solConfiguration 2 }


         solBladeTable OBJECT-TYPE
                    SYNTAX  SEQUENCE OF SolBladeEntry
                    MAX-ACCESS  not-accessible
                    STATUS  current -- was mandatory
                    DESCRIPTION
                    "SOL Blade configuration table."
                    ::= { solBladeConfig 1 }

         solBladeEntry  OBJECT-TYPE
                    SYNTAX  SolBladeEntry
                    MAX-ACCESS  not-accessible
                    STATUS  current -- was mandatory
                    DESCRIPTION
                    "SOL Blade table entry"
                    INDEX { solBladeIndex }
                    ::= { solBladeTable 1 }

         SolBladeEntry ::= SEQUENCE {
                    solBladeIndex   INTEGER, 
                    solBladeName    OCTET STRING,
                    solBladeEnable  INTEGER,
                    solBladeIpAddr  IpAddress, 
                    solBladeSessionStatus  INTEGER,
                    solBladeCapability  INTEGER 
                    }

         solBladeIndex OBJECT-TYPE
                    SYNTAX  Integer32 (0..2147483647) -- was INTEGER
                    MAX-ACCESS  read-only
                    STATUS  current -- was mandatory
                    DESCRIPTION
                    "SOL Blade table index."
                    ::= { solBladeEntry 1 }

         solBladeName OBJECT-TYPE
                    SYNTAX  OCTET STRING
                    MAX-ACCESS  read-only
                    STATUS  current -- was mandatory
                    DESCRIPTION
                    "The name of the blade as a null terminated string."
                    ::= { solBladeEntry 2 }

         solBladeEnable  OBJECT-TYPE
                    SYNTAX  INTEGER {
                      solBladeDisabled(0),
                      solBladeEnabled(1)
                    }
                    MAX-ACCESS  read-write
                    STATUS  current -- was mandatory
                    DESCRIPTION
                    "Disable or enable a SOL on a blade."
                    ::= { solBladeEntry 3 }

         solBladeIpAddr   OBJECT-TYPE
                    SYNTAX  IpAddress
                    MAX-ACCESS  read-only
                    STATUS  current -- was mandatory
                    DESCRIPTION
                    "IP address of the blade derived from the IP address range for the blade 
                    system management processors on the blades."
                    ::= { solBladeEntry 4 }

         solBladeSessionStatus OBJECT-TYPE
                    SYNTAX  INTEGER {
                      solSessionNotReady(0),
                      solSessionReady(1),
                      solSessionActive(2)
                    }
                    MAX-ACCESS  read-only
                    STATUS  current -- was mandatory
                    DESCRIPTION
                    "Status of a blade SOL session:
                       solSessionNotReady: no SOL session connected to the blade.
                       solSessionReady: there is an SOL session to the blade.
                       solSessionActive: there is an SOL session to the blade and there is a
                       client using the SOL session."
                    ::= { solBladeEntry 5 }
                               
         solBladeCapability OBJECT-TYPE
                    SYNTAX  INTEGER {
                      notSupport(0),
                      support(1)
                    }
                    MAX-ACCESS  read-only
                    STATUS  current -- was mandatory
                    DESCRIPTION
                    "Display whether or not the blade support SOL feature."
                    ::= { solBladeEntry 6 }
                               
 	  -- ********************************************************************************
          -- Chassis Internal Network (CIN)
          -- ********************************************************************************
	  chassisInternalNetwork OBJECT IDENTIFIER ::= { configureSP 11}

          -- Maximum number of CIN definitions supported
	  cinsSupported  OBJECT-TYPE
	            SYNTAX  INTEGER
		    MAX-ACCESS  read-only
		    STATUS  current -- was mandatory
		    DESCRIPTION
		    "Number of Chassis Internal Network (CIN) definitions supported.
		    Currently a maximum of 14 CIN definitions can be supported."
		    ::= { chassisInternalNetwork 1 }

          -- CIN Global Configuration
	  cinGlobalEnable  OBJECT-TYPE
	            SYNTAX  INTEGER {
		      cinDisabled(0),
		      cinEnabled(1)
		    }
		    MAX-ACCESS  read-write
		    STATUS  current -- was mandatory
		    DESCRIPTION
		    "Disable/Enable Chassis Internal Network (CIN) function dynamically.
                       Enabled:
                         AMM reads the CIN entries. For each enabled entry,
                           - If the CIN VLAN ID is new and does not have a CIN interface
                             created yet then create a new CIN interface based on that
                             CIN VLAN ID. Use the CIN IP address from the entry to create
                             a host route.
                           - If the CIN IP address is 0.0.0.0 then start ARP monitoring.

                         Disabled:
                            - Stop all ARP monitoring.
                            - Delete all host routes.
                            - Delete all CIN interfaces."
		    ::= { chassisInternalNetwork 2 }

          -- CIN Configuration Table
	  cinTable  OBJECT-TYPE
	            SYNTAX  SEQUENCE OF CinEntry
		    MAX-ACCESS  not-accessible
		    STATUS  current -- was mandatory
		    DESCRIPTION
		    "Chassis Internal Network (CIN) configuration table."
		    ::= { chassisInternalNetwork 3}

	     cinEntry  OBJECT-TYPE
	            SYNTAX  CinEntry
		    MAX-ACCESS  not-accessible
		    STATUS  current -- was mandatory
		    DESCRIPTION
		    "Chassis Internal Network (CIN) table entry."
                    INDEX { cinIndex }
		    ::= { cinTable 1 }

             CinEntry ::= SEQUENCE {
	            cinIndex  INTEGER,
		    cinDefExists INTEGER,
	            cinDelete INTEGER,
                    cinEnable INTEGER,
	            cinId  INTEGER,
                    cinIpAddress  IpAddress,
                    cinIpv6Address InetAddressIPv6
                    }

             cinIndex  OBJECT-TYPE
	            SYNTAX  Integer32 (0..2147483647) -- was INTEGER
		    MAX-ACCESS  read-only
		    STATUS  current -- was mandatory
		    DESCRIPTION
		    "Chassis Internal Network (CIN) table index."
	            ::= { cinEntry 1 }

	     cinDefExists  OBJECT-TYPE
                    SYNTAX  INTEGER {
                      false(0),
                      true(1)
                    }
                    MAX-ACCESS  read-only
                    STATUS  current -- was mandatory
                    DESCRIPTION
                    "Indicates if a Chassis Internal Network (CIN) definition exists for
		    this index or not."
                    ::= { cinEntry 2 }

	     cinDelete  OBJECT-TYPE
	            SYNTAX  INTEGER {
		            execute(1)
	            }
	            MAX-ACCESS  read-write
	            STATUS  current -- was mandatory
	            DESCRIPTION
	            "Delete Chassis Internal Network (CIN) definition.  
                     Works like CIN entry disabled. However, the entry is also deleted.

                    NOTE: Value returned for the GET command is meaningless for this 
                    MIB object. Deleting a non-defined entry does nothing."
	            ::= { cinEntry 3 }

	     cinEnable  OBJECT-TYPE
	            SYNTAX  INTEGER {
		      disabled(0),
		      enabled(1)
		    }
		    MAX-ACCESS  read-write
		    STATUS  current -- was mandatory
		    DESCRIPTION
		    "Disable or enable a Chassis Internal Network (CIN) definition.
                       Enabled:
                         AMM reads the entry and creates a new CIN interface if the CIN VLAN
                         ID is new and does not have a CIN interface created yet, adds host
                         route, and monitors communication path. Start ARP monitoring if
                         IP is 0.0.0.0.

                        Disabled:
                          Delete host route. If this is the last IP address that uses the CIN
                          interface,
                            - Stop ARP monitoring if IP is 0.0.0.0.
                            - Delete the CIN interface if there is no other entry depends on it."
		    ::= { cinEntry 4 }

	     cinId  OBJECT-TYPE
	            SYNTAX  INTEGER
		    MAX-ACCESS  read-write
		    STATUS  current -- was mandatory
		    DESCRIPTION
                    "This is the Chassis Internal Network (CIN) Virtual LAN (VLAN) ID for
                    the internal management network between the Management Module, 
                    I/O Module, and the blade OS. The range of valid CIN VLAN IDs is
                    3 to 4094 (inclusive). This value cannot be the same as the 
                    Serial Over LAN (SOL) or Concurrent KVM (cKVM) VLAN ID.

		    NOTE: If creating a new CIN definition, you must define cinId
		    before you define cinIpAddress.

		    NOTE: Before changing this value on an existing CIN definition,
		    you must first disable the definition."
	            ::= { cinEntry 5 }

	   cinIpAddress    OBJECT-TYPE
                    SYNTAX  IpAddress
                    MAX-ACCESS  read-write
                    STATUS  current -- was mandatory
                    DESCRIPTION
                    "Chassis Internal Network (CIN) IP address.
		  
		     Restrictions:
                       - CIN entries cannot have matching IP addresses, with the exception of 0.0.0.0. 
                       - Multiple IP addresses of 0.0.0.0 with different VLAN IDs are allowed.
                       - The IP address cannot be multi-cast.
                       - The IP address cannot match the AMM IP address.
                       - If the CIN IP address is 0.0.0.0, the blade IP address for CIN which is configured 
                         in the blade's OS can not be in the same subnet as that of AMM.

		    NOTE: If creating a new CIN definition, you must define cinId
		    before you define cinIpAddress.

                    NOTE: Before changing this value on an existing CIN definition,
                    you must first disable the definition.
                    NOTE: When ipv6 is enable on one interface, this column will 
                    display all zero IPv4 address"
                    ::= { cinEntry 6}
         cinIpv6Address   OBJECT-TYPE
                        SYNTAX  InetAddressIPv6
                        MAX-ACCESS  read-write
                        STATUS  current -- was mandatory
                        DESCRIPTION
                        "Chassis Internal Network (CIN) IPv6 address
                        
                        NOTE: When ipv4 is enable on one interface,this column will display
                        all zero IPv6 address.
                        "
                        ::= { cinEntry 7}

          -- CIN Status Table
	  cinStatus  OBJECT IDENTIFIER ::= { chassisInternalNetwork 4 }

            cinStatusTable  OBJECT-TYPE
                    SYNTAX  SEQUENCE OF CinStatusEntry
                    MAX-ACCESS  not-accessible
                    STATUS  current -- was mandatory
                    DESCRIPTION
                    "Table of Chassis Internal Network (CIN) status entry information."
                    ::= { cinStatus 1 }

            cinStatusEntry OBJECT-TYPE
                    SYNTAX CinStatusEntry
                    MAX-ACCESS  not-accessible
                    STATUS  current -- was mandatory
                    DESCRIPTION
                    "Chassis Internal Network (CIN) status table entry."
                    INDEX { cinStatusIndex }
                    ::= { cinStatusTable 1 }

            CinStatusEntry ::= SEQUENCE {
                    cinStatusIndex  INTEGER,
		    cinStatusString OCTET STRING
                    }

            cinStatusIndex  OBJECT-TYPE
                    SYNTAX  Integer32 (0..2147483647) -- was INTEGER
                    MAX-ACCESS  read-only
                    STATUS  current -- was mandatory
                    DESCRIPTION
                    "The Chassis Internal Network (CIN) status log index number.  
                    For consistent results, view as a table and not as individual entries."
                    ::= { cinStatusEntry 1 }

            cinStatusString  OBJECT-TYPE
	            SYNTAX  OCTET STRING
	            MAX-ACCESS  read-only
	            STATUS  current -- was mandatory
	            DESCRIPTION
		    "Status of a Chassis Internal Network (CIN) connection. For example:

		    Index:1 VLANID:4094 IPADDR:192.168.70.100 MAC:01:0A:0B:00:01:01 Type:Learned Status:Operational
		  
		    Index is the status entry number in the status table. Followed by the 
                    VLAN ID, IP address, and MAC address that the Management Module is
		    communicating with on the CIN connection. 

		    Type is either 'Configured' or 'Learned'. Learned implies that the
		    Management Module dynamically discovered the IP address. 
		    Configured means that the address was explicitly configured in 
		    the Management Module. 

		    Status can be 'Operational', 'Not Operational', or 'Disabled'.

                    'Operational' means the Management Module can ping the CIN IP address.

		    'Not Operational' means that the Management Module cannot ping the CIN
		    IP address. Verify that the blade and I/O Module are configured properly
		    and that their configurations are compatible with the Management Module.
		    The blade OS also needs to have an IP host route defined
		    (e.g. route add -host 192.168.70.100 eth0.4094).
		    I/O Modules need to have a VLAN defined containing the blade's and the
		    AMM's port. Blade and I/O Modules need to be powered up and operational.

                    'Disabled' means that the CIN configuration has been disabled by a
		    Management Module administrator.

                    For consistent results, view as a table and not as individual entries."
                    ::= { cinStatusEntry 2 } 
	
          -- ********************************************************************************
          -- SNMP (Ers) Configuration
          -- ********************************************************************************
          configurationManagement       OBJECT IDENTIFIER ::= { configureSP 15 }
          saveConfigurationToChassis  OBJECT-TYPE
                      SYNTAX  INTEGER {
                              compressedFormat(1),
                              legacyFormat(2)         -- deprecated
                      }
                      MAX-ACCESS read-write
                      STATUS  current -- was mandatory
                      DESCRIPTION
                      "Save the configuration settings from the AMM to the chassis.
                      This operation may take several seconds.
                      The input values for the SET command when AMM is installed in BladeCenter and 
                      BladeCenter T are:
                         1: Save the configuration settings in compressed(AMM) format.
                         2: Save the configuration settings in legacy(MM) format. This option has 
                         been deprecated.
                         other: Invalid.

                      The input values for the SET command when AMM is installed in BladeCenter H and 
                      BladeCenter HT are:
                         1: Save the configuration settings in compressed(AMM) format.
                         other: Invalid.

                      NOTE: This MIB object is for AMM only and the value returned for the GET command is meaningless."
                      ::= { configurationManagement 1 }
                    
          restoreConfigurationFromChassis OBJECT-TYPE
                      SYNTAX  INTEGER {
                             execute(1)                             
                      }
                      MAX-ACCESS  read-write
                      STATUS  current -- was mandatory
                      DESCRIPTION
                      "Restore the configuration settings to the AMM from the BladeCenter chassis.         
                      NOTE: This MIB object is for AMM only and the value returned for the GET command is meaningless."
                      ::= { configurationManagement 2 }         


          autoReadConfigInNewChassis  OBJECT-TYPE
                      SYNTAX  INTEGER {
                              disabled(0),
                              enabled(1)
                      }
                      MAX-ACCESS read-write
                      STATUS  current -- was mandatory
                      DESCRIPTION
                      "The AMM will automatically read configuration settings
                      from the midplane every time the AMM is inserted into a
                      new chassis.
                      NOTE: This MIB object is for AMM only."
                      ::= { configurationManagement 3 }


     -- ************************************************************************
     -- BladeCenter T System Management
     -- ************************************************************************

     -- ************************************************************************
    
     telcoAlarmReq OBJECT IDENTIFIER ::= { telcoManagement 1 }


     -- ************************************************************************
     -- BladeCenter T Set A Software Alarm
     -- ************************************************************************
     telcoAlarmSet OBJECT-TYPE
                   SYNTAX  OCTET STRING 
                   MAX-ACCESS  read-write
                   STATUS  current -- was mandatory
                   DESCRIPTION
                   "Create a software alarm. An input octet string consists of the 
                   alarm severity level and the alarm description (40 bytes max).
                   The following severity levels are valid :
                        CRT Critical 
                        MJR Major 
                        MNR Minor
                        
                   NOTE 1: Value returned for the GET command is meaningless for 
                   this MIB object.
                   
                   NOTE 2: This MIB object is for BladeCenter T only."
                   ::= { telcoAlarmReq 1 }
     

     -- ************************************************************************
     -- BladeCenter T Ack an Alarm
     -- ************************************************************************
     telcoAlarmAck OBJECT-TYPE
                   SYNTAX  OCTET STRING 
                   MAX-ACCESS  read-write
                   STATUS  current -- was mandatory
                   DESCRIPTION
                   "Acknowledge an alarm. An input octet string consists of the 
                   alarm key ID expressed as 'mmm:ggg:iii:aaa:sss' where: 
                      m : Module ID value of decimal digits(1-255) or 
                          blank space(s) for leading zero(s)
                      g : Gen ID value of decimal digits(1-255) or 
                          blank space(s) for leading zero(s)
                      i : GenInfo ID value of decimal digits(1-255) or
                          blank space(s) for leading zero(s)
                      a : Alarm ID value of decimal digits(1-255) or
                          blank space(s) for leading zero(s) 
                      s : Alarm severity value of decimal digits(1-255) or
                          blank space(s) for leading zero(s) 
    
                          
                   NOTE 1: Value returned for the GET command is meaningless for 
                   this MIB object.
                     
                   NOTE 2: This MIB object is for BladeCenter T only."
                   ::= { telcoAlarmReq 2 }
                   

     -- ************************************************************************
     -- BladeCenter T Clear an Alarm
     -- ************************************************************************
     telcoAlarmClear OBJECT-TYPE
                   SYNTAX  OCTET STRING 
                   MAX-ACCESS  read-write
                   STATUS  current -- was mandatory
                   DESCRIPTION
                   "Clear an active alarm. An input octet string consists of the 
                   alarm key ID expressed as 'mmm:ggg:iii:aaa:sss' where: 
                      m : Module ID value of decimal digits(1-255) or 
                          blank space(s) for leading zero(s)
                      g : Gen ID value of decimal digits(1-255) or 
                          blank space(s) for leading zero(s)
                      i : GenInfo ID value of decimal digits(1-255) or
                          blank space(s) for leading zero(s)
                      a : Alarm ID value of decimal digits(1-255) or
                          blank space(s) for leading zero(s)    
                      s : Alarm severity value of decimal digits(1-255) or
                          blank space(s) for leading zero(s) 
                          
                          
                   NOTE1 : Value returned for the GET command is meaningless for 
                   this MIB object.
                     
                   NOTE 2: This MIB object is for BladeCenter T only."
                   ::= { telcoAlarmReq 3 }
      


     -- ************************************************************************
     -- ************************************************************************
     -- BladeCenter HT Hardware Operation Management  
     -- ************************************************************************
    
       telcoHWManagement OBJECT IDENTIFIER ::= { telcoManagement 3 }

     -- ********************************************************************************
     -- Telco Alarm Panel Power ON/OFF operation   
     -- ********************************************************************************
       
       tappowerReq OBJECT IDENTIFIER ::= { telcoHWManagement 1 }

       tappoweronoff OBJECT-TYPE
                      SYNTAX  INTEGER {
                        poweroff(0),
                        poweron(1)
                      }
                      MAX-ACCESS  read-write
                      STATUS  current -- was mandatory
                      DESCRIPTION
                      "Telco Alarm Panel power on or power off.  If powering off a currently
                      powered on Telco Alarm Panel, then all LEDs of this request card will 
                      be reset to OFF and the Safely Remove LED will be turned ON to indicate 
                      the card is safe for removal.
                      NOTE: This MIB object is for BladeCenter HT only.
                      NOTE: Value returned for the GET command is meaningless for this MIB object."
                      ::= { tappowerReq 1}


     -- ********************************************************************************
     -- Network Clock Power ON/OFF operation   
     -- ********************************************************************************
       
       ncReq OBJECT IDENTIFIER ::= { telcoHWManagement 2 }

     
     -- ********************************************************************************
     -- Network Clock Cards                  
     -- ****************************************************************************
     
       ncReqTable OBJECT-TYPE
                      SYNTAX  SEQUENCE OF NcReqEntry
                      MAX-ACCESS  not-accessible
                      STATUS  current -- was mandatory
                      DESCRIPTION
                      "Table of the Network Clock Module Operations.
                      For consistent results, view as a table and not as individual entries.
                      
                      NOTE: This MIB object is for BladeCenter HT only." 
                      ::= { ncReq 1 }

       ncReqEntry OBJECT-TYPE
                      SYNTAX NcReqEntry
                      MAX-ACCESS  not-accessible
                      STATUS  current -- was mandatory
                      DESCRIPTION
                      "Network Clock Module Power ON/OFF entry.
                      For consistent results, view as a table and not as individual entries.
                      
                      NOTE: This MIB object is for BladeCenter HT only." 
                      INDEX { ncReqIndex }
                      ::= { ncReqTable 1 }

       NcReqEntry ::= SEQUENCE {
                          ncReqIndex INTEGER,
                          ncReqBayNumber INTEGER,
                          ncReqPoweronoff INTEGER
                          }

     
       ncReqIndex OBJECT-TYPE
                      SYNTAX  INTEGER (0..128)
                      MAX-ACCESS  read-only
                      STATUS  current -- was mandatory
                      DESCRIPTION
                      "Network Clock Module Request index.
                      For consistent results, view as a table and not as individual entries.
                      
                      NOTE: This MIB object is for BladeCenter HT only." 
                      ::= { ncReqEntry 1 }

       ncReqBayNumber  OBJECT-TYPE
                      SYNTAX  INTEGER {
                           networkclock1(1),
                           networkclock2(2)
                      }
                      MAX-ACCESS  read-only
                      STATUS  current -- was mandatory
                      DESCRIPTION
                      "Network Clock Module Request Bay number.
                      For consistent results, view as a table and not as individual entries.
                      
                      NOTE: This MIB object is for BladeCenter HT only." 
                      ::= { ncReqEntry 2 } 

       ncReqPoweronoff OBJECT-TYPE
                      SYNTAX  INTEGER {
                           poweroff(0),
                           poweron(1)
                      }
                      MAX-ACCESS  read-write
                      STATUS  current -- was mandatory
                      DESCRIPTION
                      "Request to power on/off for the specified Network Clock Module. 
                      For consistent results, view as a table and not as individual entries.
                      NOTE: This MIB object is for BladeCenter HT only.
                      NOTE: Value returned for the GET command is meaningless for this MIB object."
                      ::= { ncReqEntry 3 }



     -- ************************************************************************
     -- BladeCenter T OEM grouping
     -- ************************************************************************
    
     telcoOEM OBJECT IDENTIFIER ::= { telcoManagement 127 }
     
     telcoOEMs                   OBJECT-TYPE
                                 SYNTAX  OCTET STRING
                                 MAX-ACCESS  read-only
                                 STATUS  current -- was mandatory
                                 DESCRIPTION
                                 "A bitmap of information about the contents of this subtree. The 
                                 bitmap is a variable length string containing a list of 1's and 0's.
                                 Every bit that is set to 1 has a corresponding subtree entry that
                                 is supported in firmware, while a 0 means that the subtree entry
                                 is unavailable.
                                 
                                 NOTE: This MIB object is for BladeCenter T only."
                                 ::= { telcoOEM 1 }

     
  --  ********************************************************************************
  --  Restart Control
  --  ********************************************************************************

      restartSPImmediately   OBJECT-TYPE
                     SYNTAX  INTEGER {
                      execute(1)
                     }
                     MAX-ACCESS  read-write
                     STATUS  current -- was mandatory
                     DESCRIPTION
                     "Restart the MM immediately.
                     
                     NOTE: Value returned for the GET command is meaningless for 
                     this MIB object."
                     ::= { restartReset 4 }

     restartStandbyMM  OBJECT-TYPE
                    SYNTAX  INTEGER {
                      execute(1)
                     }
                    MAX-ACCESS  read-write
                    STATUS  current -- was mandatory
                    DESCRIPTION
                    "Restarts the Standby MM from the Primary MM.

                    NOTE: Value returned for the GET command is meaningless for 
                    this MIB object.

                    NOTE: This mib object is only applicable to systems with a standby MM."
                    ::= { restartReset 5}

      switchOverRedundantMM  OBJECT-TYPE
                     SYNTAX  INTEGER {
                      execute(1)
                     }
                     MAX-ACCESS  read-write
                     STATUS  current -- was mandatory
                     DESCRIPTION
                     "Switch over to the redundant Management Module.
                     The failover will not occur if the standby or primary MM is in flashing mode.
                     
                     NOTE: Value returned for the GET command is meaningless for 
                     this MIB object.

                     NOTE: This mib object is only applicable to systems with a redundant MM."
                     ::= { restartReset 7 }

      resetSPConfigAndRestart  OBJECT-TYPE
                    SYNTAX  INTEGER {
                      execute(1)
                     }
                    MAX-ACCESS  read-write
                    STATUS  current -- was mandatory
                    DESCRIPTION
                    "Will cause all the MM information to be reset to it's
                    initial factory defaults (all previous configuration
                    information is lost) and the MM will be re-started.
                    
                    NOTE: Value returned for the GET command is meaningless 
                    for this MIB object."
                    ::= { restartReset 20 }
      
      resetSPConfigAndRestartSaveLogs  OBJECT-TYPE
                    SYNTAX  INTEGER {
                      execute(1)
                     }
                    MAX-ACCESS  read-write
                    STATUS  current -- was mandatory
                    DESCRIPTION
                    "Will cause all the MM information to be reset to it's
                    initial factory defaults (all previous configuration
                    information is lost) and the MM will be re-started. The 
                    logs will be saved.
                    
                    NOTE: Value returned for the GET command is meaningless 
                    for this MIB object."
                    ::= { restartReset 21 }

  --  ********************************************************************************
  --  processorBlade
  --  ********************************************************************************
    --This group of objects provides information specific to blades
    processorBlade OBJECT IDENTIFIER ::= { blades 1 }

      -- ********************************************************************************
      -- Media and I/O
      -- ********************************************************************************
      bladeMediaTrayBladeId  OBJECT-TYPE
                     SYNTAX  INTEGER {
                       managementModule(0),
                       blade1(1),
                       blade2(2),
                       blade3(3),
                       blade4(4),
                       blade5(5),
                       blade6(6),
                       blade7(7),
                       blade8(8),
                       blade9(9),
                       blade10(10),
                       blade11(11),
                       blade12(12),
                       blade13(13),
                       blade14(14)
                     }
                     MAX-ACCESS  read-write
                     STATUS  current -- was mandatory
                     DESCRIPTION
                     "Allocate the media tray to a blade of a BladeCenter system.
                     On a get command, a blade ID of 0x00 means that no blade is
                     currently using the device.  A set command cannot allocate
                     the media tray to the management module.

                     NOTE: A blade cannot be allocated to the media tray if the 
                     value of OID remoteMediaTraySwitchEnable of the blade is disabled."
                     ::= { processorBlade 1 }

      bladeKVMBladeId  OBJECT-TYPE
                     SYNTAX  INTEGER {
                       managementModule(0),
                       blade1(1),
                       blade2(2),
                       blade3(3),
                       blade4(4),
                       blade5(5),
                       blade6(6),
                       blade7(7),
                       blade8(8),
                       blade9(9),
                       blade10(10),
                       blade11(11),
                       blade12(12),
                       blade13(13),
                       blade14(14)
                     }
                     MAX-ACCESS  read-write
                     STATUS  current -- was mandatory
                     DESCRIPTION
                     "Allocate the keyboard, video, and mouse ports (KVM) to a blade
                     of a blade runner system.  On a get command, a blade ID of 0x00
                     means that no blade is currently using the devices.  A set
                     command cannot allocate the KVM to the management module."
                     ::= { processorBlade 2 }

      -- ********************************************************************************
      -- Blade boot sequence
      -- ********************************************************************************
      bladeBootSequenceTable OBJECT-TYPE
                     SYNTAX  SEQUENCE OF BladeBootSequenceEntry
                     MAX-ACCESS  not-accessible
                     STATUS  current -- was mandatory
                     DESCRIPTION
                     "Table of blade boot sequence information.  Contains
                     the boot sequence information for each blade."
                     ::= { processorBlade 3 }

       bladeBootSequenceEntry OBJECT-TYPE
                     SYNTAX BladeBootSequenceEntry
                     MAX-ACCESS  not-accessible
                     STATUS  current -- was mandatory
                     DESCRIPTION
                     "Boot sequence entry"
                     INDEX { bootSequenceIndex }
                     ::= { bladeBootSequenceTable 1 }


       BladeBootSequenceEntry ::= SEQUENCE {
                   bootSequenceIndex INTEGER,
                   bootSequenceBladeId INTEGER,
                   bootSequenceBladeExists INTEGER,
                   bootSequenceBladePowerState INTEGER,
                   bootSequenceBladeHealthState INTEGER,
                   bootSequenceBladeName OCTET STRING,
                   bootSequence1 INTEGER,
                   bootSequence2 INTEGER,
                   bootSequence3 INTEGER,
                   bootSequence4 INTEGER
                   }

       bootSequenceIndex  OBJECT-TYPE
                   SYNTAX  Integer32 (0..2147483647) -- was INTEGER
                   MAX-ACCESS  read-only
                   STATUS  current -- was mandatory
                   DESCRIPTION
                   "Blade boot sequence index."
                   ::= { bladeBootSequenceEntry 1 }

       bootSequenceBladeId   OBJECT-TYPE
                   SYNTAX  INTEGER {
                       blade1(1),
                       blade2(2),
                       blade3(3),
                       blade4(4),
                       blade5(5),
                       blade6(6),
                       blade7(7),
                       blade8(8),
                       blade9(9),
                       blade10(10),
                       blade11(11),
                       blade12(12),
                       blade13(13),
                       blade14(14)
                     }
                   MAX-ACCESS  read-only
                   STATUS  current -- was mandatory
                   DESCRIPTION
                   "The numeric blade ID."
                   ::= { bladeBootSequenceEntry 2 }

       bootSequenceBladeExists OBJECT-TYPE
                   SYNTAX  INTEGER {
                     false(0),
                     true(1)
                   }
                   MAX-ACCESS  read-only
                   STATUS  current -- was mandatory
                   DESCRIPTION
                   "Indicates whether the server blade specified exists or not."
                   ::= { bladeBootSequenceEntry 3 }

       bootSequenceBladePowerState OBJECT-TYPE
                   SYNTAX  INTEGER {
                     off(0),
                     on(1),
                     standby(3),
                     hibernate(4)                     
                   }
                   MAX-ACCESS  read-only
                   STATUS  current -- was mandatory
                   DESCRIPTION
                   "Indicates the power state of the blade specified."
                   ::= { bladeBootSequenceEntry 4 }

       bootSequenceBladeHealthState  OBJECT-TYPE
                   SYNTAX  INTEGER {
                     unknown(0),
                     good(1),
                     warning(2),
                     critical(3),
                     kernelMode(4),
                     discovering(5),
                     commError(6),
                     noPower(7),
                     flashing(8),
                     initFailure(9),
                     insufficientPower(10),
                     powerDenied(11)
                   }
                   MAX-ACCESS  read-only
                   STATUS  current -- was mandatory
                   DESCRIPTION
                   "The system health state for the blade.

                    Unknown: Blade is in an undefined state.
                    Good: Blade is operating normally.
                    Warning: One or more outstanding warnings exist for this blade.
                    Critical: One or more outstanding critical events for this blade.
                    Kernel Mode: Blade is in kernel mode.
                    Discovering: The AMM is currently in the process of discovering this blade.
                    Communications Error: The AMM failed to communicate with this blade.
                    No Power: No power to the blade's domain.
                    Flashing: Flashing in progress.
                    Initialization Failure: Blade failed to initialized.
                    Insufficient Power: Not enough power is left in the blade's domain to power the blade.
                    Power Denied: Power was denied to the blade."
                 ::= { bladeBootSequenceEntry 5 }

       bootSequenceBladeName OBJECT-TYPE
                   SYNTAX  OCTET STRING
                   MAX-ACCESS  read-only
                   STATUS  current -- was mandatory
                   DESCRIPTION
                   "The name of the blade as a null terminated string."
                   ::= { bladeBootSequenceEntry 6 }

       bootSequence1 OBJECT-TYPE
                   SYNTAX  INTEGER {
                     noneSpecified(0),
                     floppy(1),
                     cdrom(2),
                     hardDrive0(3),
                     hardDrive1(4),
                     hardDrive2(5),
                     hardDrive3(6),
                     networkBoot(7),
                     iscsi(8),
                     iscsiCritical(9),
                     hardDrive4(10),
                     usbModularFlashDrive(11),
                     notAvailable(255)
                   }
                   MAX-ACCESS  read-write
                   STATUS  current -- was mandatory
                   DESCRIPTION
                   "The boot device for this blade boot sequence. Note that some types
                   of blades don't support floppy disk drive. It is recommended that all
                   boot sequence 1,2 3, and 4 be configured starting from boot sequence 1.
                   If there is any duplication of the configured boot sequence and the 
                   current configuration, the two boot sequence will be swapped. 
                   For an example: the current boot sequence is
                        1=HD0, 2=CD, 3=FD, 4=HD1
                   If the user wants to configure 1=FD which is a duplication of 3 then the
                   new boot sequence will be:
                        1=FD, 2=CD, 3=HD0, 4=HD1  (1 and 3 swapped)
                   Not all hard drives are available on all blade configurations.
                   The 'Iscsi critical' option has a special meaning: the blade tries to 
                   find an iscsi boot device and if it does not it keeps trying forever."
                   ::= { bladeBootSequenceEntry 7 }

       bootSequence2 OBJECT-TYPE
                   SYNTAX  INTEGER {
                     noneSpecified(0),
                     floppy(1),
                     cdrom(2),
                     hardDrive0(3),
                     hardDrive1(4),
                     hardDrive2(5),
                     hardDrive3(6),
                     networkBoot(7),
                     iscsi(8),
                     iscsiCritical(9),
                     hardDrive4(10),
                     usbModularFlashDrive(11),
                     notAvailable(255)
                   }
                   MAX-ACCESS  read-write
                   STATUS  current -- was mandatory
                   DESCRIPTION
                   "The boot device for this blade boot sequence. Note that some types
                   of blades don't support floppy disk drive. It is recommended that all
                   boot sequence 1,2 3, and 4 be configured starting from boot sequence 1.
                   If there is any duplication of the configured boot sequence and the 
                   current configuration, the two boot sequence will be swapped. 
                   For an example: the current boot sequence is
                        1=HD0, 2=CD, 3=FD, 4=HD1
                   If the user wants to configure 1=FD which is a duplication of 3 then the
                   new boot sequence will be:
                        1=FD, 2=CD, 3=HD0, 4=HD1  (1 and 3 swapped)
                   Not all hard drives are available on all blade configurations.
                   The 'Iscsi critical' option has a special meaning: the blade tries to 
                   find an iscsi boot device and if it does not it keeps trying forever."
                   ::= { bladeBootSequenceEntry 8 }

       bootSequence3 OBJECT-TYPE
                   SYNTAX  INTEGER {
                     noneSpecified(0),
                     floppy(1),
                     cdrom(2),
                     hardDrive0(3),
                     hardDrive1(4),
                     hardDrive2(5),
                     hardDrive3(6),
                     networkBoot(7),
                     iscsi(8),
                     iscsiCritical(9),
                     hardDrive4(10),
                     usbModularFlashDrive(11),
                     notAvailable(255)
                   }
                   MAX-ACCESS  read-write
                   STATUS  current -- was mandatory
                   DESCRIPTION
                   "The boot device for this blade boot sequence. Note that some types
                   of blades don't support floppy disk drive. It is recommended that all
                   boot sequence 1,2 3, and 4 be configured starting from boot sequence 1.
                   If there is any duplication of the configured boot sequence and the 
                   current configuration, the two boot sequence will be swapped. 
                   For an example: the current boot sequence is
                        1=HD0, 2=CD, 3=FD, 4=HD1
                   If the user wants to configure 1=FD which is a duplication of 3 then the
                   new boot sequence will be:
                        1=FD, 2=CD, 3=HD0, 4=HD1  (1 and 3 swapped)
                   Not all hard drives are available on all blade configurations.
                   The 'Iscsi critical' option has a special meaning: the blade tries to 
                   find an iscsi boot device and if it does not it keeps trying forever."
                   ::= { bladeBootSequenceEntry 9 }

       bootSequence4 OBJECT-TYPE
                   SYNTAX  INTEGER {
                     noneSpecified(0),
                     floppy(1),
                     cdrom(2),
                     hardDrive0(3),
                     hardDrive1(4),
                     hardDrive2(5),
                     hardDrive3(6),
                     networkBoot(7),
                     iscsi(8),
                     iscsiCritical(9),
                     hardDrive4(10),
                     usbModularFlashDrive(11),
                     notAvailable(255)
                   }
                   MAX-ACCESS  read-write
                   STATUS  current -- was mandatory
                   DESCRIPTION
                   "The boot device for this blade boot sequence. Note that some types
                   of blades don't support floppy disk drive. It is recommended that all
                   boot sequence 1,2 3, and 4 be configured starting from boot sequence 1.
                   If there is any duplication of the configured boot sequence and the 
                   current configuration, the two boot sequence will be swapped. 
                   For an example: the current boot sequence is
                        1=HD0, 2=CD, 3=FD, 4=HD1
                   If the user wants to configure 1=FD which is a duplication of 3 then the
                   new boot sequence will be:
                        1=FD, 2=CD, 3=HD0, 4=HD1  (1 and 3 swapped)
                   Not all hard drives are available on all blade configurations.
                   The 'Iscsi critical' option has a special meaning: the blade tries to 
                   find an iscsi boot device and if it does not it keeps trying forever."
                   ::= { bladeBootSequenceEntry 10 }

      -- ********************************************************************************
      -- Blade local control
      -- ********************************************************************************
      bladeRemoteControl OBJECT IDENTIFIER ::= { processorBlade 4 }
       -- remote blade control

        bladeRemoteControlTable OBJECT-TYPE
                       SYNTAX  SEQUENCE OF BladeRemoteControlEntry
                       MAX-ACCESS  not-accessible
                       STATUS  current -- was mandatory
                       DESCRIPTION
                       "Table of blade remote power control information.
                       Contains power on/off enablement status for each blade."
                       ::= { bladeRemoteControl 1 }

         bladeRemoteControlEntry OBJECT-TYPE
                       SYNTAX BladeRemoteControlEntry
                       MAX-ACCESS  not-accessible
                       STATUS  current -- was mandatory
                       DESCRIPTION
                       "Remote power control entry"
                       INDEX { remoteControlIndex }
                       ::= { bladeRemoteControlTable 1 }


         BladeRemoteControlEntry ::= SEQUENCE {
                     remoteControlIndex INTEGER,
                     remoteControlBladeId INTEGER,
                     remoteControlBladeExists INTEGER,
                     remoteControlBladePowerState INTEGER,
                     remoteControlBladeHealthState INTEGER,
                     remoteControlBladeName OCTET STRING,
                     remotePowerControlEnable INTEGER,
                     remoteMediaTrayControlEnable INTEGER,
                     remoteKVMControlEnable INTEGER,
                     remoteWakeOnLanControlEnable INTEGER,
                     remoteMediaTraySwitchEnable INTEGER
         }

         remoteControlIndex  OBJECT-TYPE
                     SYNTAX  Integer32 (0..2147483647) -- was INTEGER
                     MAX-ACCESS  read-only
                     STATUS  current -- was mandatory
                     DESCRIPTION
                     "Blade remote power control index."
                     ::= { bladeRemoteControlEntry 1 }


         remoteControlBladeId  OBJECT-TYPE
                     SYNTAX  INTEGER {
                       blade1(1),
                       blade2(2),
                       blade3(3),
                       blade4(4),
                       blade5(5),
                       blade6(6),
                       blade7(7),
                       blade8(8),
                       blade9(9),
                       blade10(10),
                       blade11(11),
                       blade12(12),
                       blade13(13),
                       blade14(14)
                     }
                     MAX-ACCESS  read-only
                     STATUS  current -- was mandatory
                     DESCRIPTION
                     "The numeric blade ID."
                     ::= { bladeRemoteControlEntry 2 }

         remoteControlBladeExists OBJECT-TYPE
                     SYNTAX  INTEGER {
                       false(0),
                       true(1)
                     }
                     MAX-ACCESS  read-only
                     STATUS  current -- was mandatory
                     DESCRIPTION
                     "Indicates whether the server blade specified exists or not."
                     ::= { bladeRemoteControlEntry 3 }

         remoteControlBladePowerState OBJECT-TYPE
                     SYNTAX  INTEGER {
                       off(0),
                       on(1),
                       standby(3),
                       hibernate(4),                       
                       unknown(255)
                     }
                     MAX-ACCESS  read-only
                     STATUS  current -- was mandatory
                     DESCRIPTION
                     "The power state for blade.
                     0 = off, 1 = on, 3 = standby, 4 = hibernate, 255 = unknown."
                     ::= { bladeRemoteControlEntry 4 }

         remoteControlBladeHealthState  OBJECT-TYPE
                   SYNTAX  INTEGER {
                     unknown(0),
                     good(1),
                     warning(2),
                     critical(3),
                     kernelMode(4),
                     discovering(5),
                     commError(6),
                     noPower(7),
                     flashing(8),
                     initFailure(9),
                     insufficientPower(10),
                     powerDenied(11)
                   }
                   MAX-ACCESS  read-only
                   STATUS  current -- was mandatory
                   DESCRIPTION
                   "The system health state for the blade.

                    Unknown: Blade is in an undefined state.
                    Good: Blade is operating normally.
                    Warning: One or more outstanding warnings exist for this blade.
                    Critical: One or more outstanding critical events for this blade.
                    Kernel Mode: Blade is in kernel mode.
                    Discovering: The AMM is currently in the process of discovering this blade.
                    Communications Error: The AMM failed to communicate with this blade.
                    No Power: No power to the blade's domain.
                    Flashing: Flashing in progress.
                    Initialization Failure: Blade failed to initialized.
                    Insufficient Power: Not enough power is left in the blade's domain to power the blade.
                    Power Denied: Power was denied to the blade."
                   ::= { bladeRemoteControlEntry 5 }

         remoteControlBladeName OBJECT-TYPE
                     SYNTAX  OCTET STRING
                     MAX-ACCESS  read-only
                     STATUS  current -- was mandatory
                     DESCRIPTION
                     "The name of the blade as a null terminated string."
                     ::= { bladeRemoteControlEntry 6 }

         remotePowerControlEnable OBJECT-TYPE
                     SYNTAX  INTEGER {
                       disabled(0),
                       enabled(1)
                     }
                     MAX-ACCESS  read-write
                     STATUS  current -- was mandatory
                     DESCRIPTION
                     "Blade remote power control enablement status."
                     ::= { bladeRemoteControlEntry 7 }

         remoteMediaTrayControlEnable OBJECT-TYPE
                     SYNTAX  INTEGER {
                       disabled(0),
                       enabled(1)
                     }
                     MAX-ACCESS  read-write
                     STATUS  current -- was mandatory
                     DESCRIPTION
                     "Blade media tray enablement status."
                     ::= { bladeRemoteControlEntry 8 }


         remoteKVMControlEnable OBJECT-TYPE
                     SYNTAX  INTEGER {
                       disabled(0),
                       enabled(1)
                     }
                     MAX-ACCESS  read-write
                     STATUS  current -- was mandatory
                     DESCRIPTION
                     "Blade KVM enablement status. Note that some types of blades
                     don't support KVM"
                     ::= { bladeRemoteControlEntry 9 }

         remoteWakeOnLanControlEnable OBJECT-TYPE
                     SYNTAX  INTEGER {
                       disabled(0),
                       enabled(1),
                       notApplicable(255)
                     }
                     MAX-ACCESS  read-write
                     STATUS  current -- was mandatory
                     DESCRIPTION
                     "Blade Wake On LAN enablement status.
                     If WOL is not supported by the blade, it displays 'notApplicable'
                     and WOL can not be enabled or disabled."
                     ::= { bladeRemoteControlEntry 10 }
                     
         remoteMediaTraySwitchEnable OBJECT-TYPE
                     SYNTAX  INTEGER {
                       disabled(0),
                       enabled(1)
                     }
                     MAX-ACCESS  read-write
                     STATUS  current -- was mandatory
                     DESCRIPTION
                     "Blade Remote Media Tray Switch enablement status. 
                     If the remote disk feature is disabled, this OID cannot be set."
                     ::= { bladeRemoteControlEntry 11 }

       bladePolicy  OBJECT IDENTIFIER ::= { bladeRemoteControl 2}
       -- global blade remote control policy

         bladePolicyPowerControlEnable OBJECT-TYPE
                     SYNTAX  INTEGER {
                       disabled(0),
                       enabled(1)
                     }
                     MAX-ACCESS  read-write
                     STATUS  current -- was mandatory
                     DESCRIPTION
                     "Blade remote power control enablement status policy."
                     ::= { bladePolicy 1 }

         bladePolicyMediaTrayControlEnable OBJECT-TYPE
                     SYNTAX  INTEGER {
                       disabled(0),
                       enabled(1)
                     }
                     MAX-ACCESS  read-write
                     STATUS  current -- was mandatory
                     DESCRIPTION
                     "Blade media tray enablement status policy."
                     ::= { bladePolicy 2 }


         bladePolicyKVMControlEnable OBJECT-TYPE
                     SYNTAX  INTEGER {
                       disabled(0),
                       enabled(1)
                     }
                     MAX-ACCESS  read-write
                     STATUS  current -- was mandatory
                     DESCRIPTION
                     "Blade KVM enablement status policy. Note that some types of blades
                     don't support KVM."
                     ::= { bladePolicy 3 }

         bladePolicyWakeOnLanControlEnable OBJECT-TYPE
                     SYNTAX  INTEGER {
                       disabled(0),
                       enabled(1),
                       notApplicable(255)
                     }
                     MAX-ACCESS  read-write
                     STATUS  current -- was mandatory
                     DESCRIPTION
                     "Blade Wake On LAN enablement status policy.
                     
                     NOTE: Value returned for the GET command is meaningless 
                     for this MIB object."
                     ::= { bladePolicy 4 }

         bladePolicyMediaTraySwitchEnable OBJECT-TYPE
                     SYNTAX  INTEGER {
                       disabled(0),
                       enabled(1)
                     }
                     MAX-ACCESS  read-write
                     STATUS  current -- was mandatory
                     DESCRIPTION
                     "Blade Remote Media Tray Switch enablement status policy. 
                     If the remote disk feature is disabled, this OID cannot be set."
                     ::= { bladePolicy 5 }

         bladePolicyMultipleRemoteVideoEnable OBJECT-TYPE
                     SYNTAX  INTEGER {
                       disabled(0),
                       enabled(1)                       
                     }
                     MAX-ACCESS  read-write
                     STATUS  current -- was mandatory
                     DESCRIPTION
                     "Blade multiple remote video sessions enablement status policy.

                     A maximum users can access the video of the same blade from remote 
                     console when set to enabled. If it is disabled, only one user can
                     access the video from remote control."                     
                     ::= { bladePolicy 6 }
                     

      -- ********************************************************************************
      -- Blade system health state params
      -- ********************************************************************************

      bladeMonitors OBJECT IDENTIFIER ::= { processorBlade 5 }

       bladeSystemStatusTable OBJECT-TYPE
                     SYNTAX  SEQUENCE OF BladeSystemStatusEntry
                     MAX-ACCESS  not-accessible
                     STATUS  current -- was mandatory
                     DESCRIPTION
                     "Table of blade status information."
                     ::= { bladeMonitors 1 }

       bladeSystemStatusEntry OBJECT-TYPE
                     SYNTAX BladeSystemStatusEntry
                     MAX-ACCESS  not-accessible
                     STATUS  current -- was mandatory
                     DESCRIPTION
                     "Blade system status entry"
                     INDEX { bladeStatusIndex }
                     ::= { bladeSystemStatusTable 1 }


       BladeSystemStatusEntry ::= SEQUENCE {
                   bladeStatusIndex INTEGER,
                   bladeId INTEGER,
                   bladeExists INTEGER,
                   bladePowerState INTEGER,
                   bladeHealthState INTEGER,
                   bladeName OCTET STRING,
                   bladeRemotePowerEnable INTEGER,
                   bladeRemoteMediaTrayEnable INTEGER,
                   bladeRemoteKVMEnable INTEGER,
                   bladeConnectionType INTEGER,
                   bladeOwnsKVM INTEGER,
                   bladeOwnsMediaTray INTEGER,
                   bladeRemoteWakeOnLanEnable INTEGER,
                   bladeServerExpansion INTEGER,
                   bladeWidth INTEGER,
                   bladeSupportCapacityOnDemand INTEGER,    -- deprecated
                   bladeServerExpansion2 INTEGER,
                   bladecKVMStatus INTEGER,
                   bladeConnectionType2 INTEGER,
                   bladeConnectionType3 INTEGER,
                   bladeConnectionType4 INTEGER,
                   bladeConnectionType5 INTEGER,
                   bladeHighSpeedConnectionType INTEGER
                   }


       bladeStatusIndex OBJECT-TYPE
                   SYNTAX  Integer32 (0..2147483647) -- was INTEGER
                   MAX-ACCESS  read-only
                   STATUS  current -- was mandatory
                   DESCRIPTION
                   "Blade system status index."
                   ::= { bladeSystemStatusEntry 1 }

       bladeId OBJECT-TYPE
                   SYNTAX  INTEGER {
                       blade1(1),
                       blade2(2),
                       blade3(3),
                       blade4(4),
                       blade5(5),
                       blade6(6),
                       blade7(7),
                       blade8(8),
                       blade9(9),
                       blade10(10),
                       blade11(11),
                       blade12(12),
                       blade13(13),
                       blade14(14)
                     }
                   MAX-ACCESS  read-only
                   STATUS  current -- was mandatory
                   DESCRIPTION
                   "The numeric blade ID."
                   ::= { bladeSystemStatusEntry 2 }

       bladeExists OBJECT-TYPE
                   SYNTAX  INTEGER {
                     false(0),
                     true(1)
                   }
                   MAX-ACCESS  read-only
                   STATUS  current -- was mandatory
                   DESCRIPTION
                   "Indicates whether the server blade specified exists or not."
                   ::= { bladeSystemStatusEntry 3 }

       bladePowerState  OBJECT-TYPE
                   SYNTAX  INTEGER {
                     off(0),
                     on(1),
                     standby(3),
                     hibernate(4)                     
                   }
                   MAX-ACCESS  read-only
                   STATUS  current -- was mandatory
                   DESCRIPTION
                   "Indicates the power state of the blade specified."
                   ::= { bladeSystemStatusEntry 4 }

       bladeHealthState  OBJECT-TYPE
                   SYNTAX  INTEGER {
                     unknown(0),
                     good(1),
                     warning(2),
                     critical(3),
                     kernelMode(4),
                     discovering(5),
                     commError(6),
                     noPower(7),
                     flashing(8),
                     initFailure(9),
                     insufficientPower(10),
                     powerDenied(11)
                   }
                   MAX-ACCESS  read-only
                   STATUS  current -- was mandatory
                   DESCRIPTION
                   "The system health state for the blade.

                    Unknown: Blade is in an undefined state.
                    Good: Blade is operating normally.
                    Warning: One or more outstanding warnings exist for this blade.
                    Critical: One or more outstanding critical events for this blade.
                    Kernel Mode: Blade is in kernel mode.
                    Discovering: The AMM is currently in the process of discovering this blade.
                    Communications Error: The AMM failed to communicate with this blade.
                    No Power: No power to the blade's domain.
                    Flashing: Flashing in progress.
                    Initialization Failure: Blade failed to initialized.
                    Insufficient Power: Not enough power is left in the blade's domain to power the blade.
                    Power Denied: Power was denied to the blade."
                   ::= { bladeSystemStatusEntry 5 }

       bladeName OBJECT-TYPE
                   SYNTAX  OCTET STRING
                   MAX-ACCESS  read-only
                   STATUS  current -- was mandatory
                   DESCRIPTION
                   "The name of the blade as a null terminated string."
                   ::= { bladeSystemStatusEntry 6 }

       bladeRemotePowerEnable  OBJECT-TYPE
                   SYNTAX  INTEGER {
                     disabled(0),
                     enabled(1)
                   }
                   MAX-ACCESS  read-only
                   STATUS  current -- was mandatory
                   DESCRIPTION
                   "Remote power state for the blade.
                   0x01 indicates enabled."
                   ::= { bladeSystemStatusEntry 7 }

       bladeRemoteMediaTrayEnable  OBJECT-TYPE
                   SYNTAX  INTEGER {
                     disabled(0),
                     enabled(1)
                   }
                   MAX-ACCESS  read-only
                   STATUS  current -- was mandatory
                   DESCRIPTION
                   "Remote Media Tray state for the blade.
                   0x01 indicates enabled."
                   ::= { bladeSystemStatusEntry 8 }

       bladeRemoteKVMEnable  OBJECT-TYPE
                   SYNTAX  INTEGER {
                     disabled(0),
                     enabled(1)
                   }
                   MAX-ACCESS  read-only
                   STATUS  current -- was mandatory
                   DESCRIPTION
                   "Remote keyboard/video/monitor state for the blade.
                   0x01 indicates enabled. Note that some types of blades
                     don't support KVM"
                   ::= { bladeSystemStatusEntry 9 }

       bladeConnectionType  OBJECT-TYPE
                   SYNTAX  INTEGER {
                     none(0),
                     ethernet(1),
                     fiber(2),
                     serial(3), 
                     opticalPassThrough(4),
                     infiniband(5), 
                     iSCSI(6)
                   }
                   MAX-ACCESS  read-only
                   STATUS  current -- was mandatory
                   DESCRIPTION
                   "Connection type of the expansion card number one."
                   ::= { bladeSystemStatusEntry 10 }

       bladeOwnsKVM  OBJECT-TYPE
                   SYNTAX  INTEGER {
                     false(0),
                     true(1)
                   }
                   MAX-ACCESS  read-only
                   STATUS  current -- was mandatory
                   DESCRIPTION
                   "Indicates whether the MM owns the KVM.
                   0 = false, 1 = true. Note that some types of blades
                     don't support KVM"
                   ::= { bladeSystemStatusEntry 11 }

       bladeOwnsMediaTray  OBJECT-TYPE
                   SYNTAX  INTEGER {
                     false(0),
                     true(1)
                   }
                   MAX-ACCESS  read-only
                   STATUS  current -- was mandatory
                   DESCRIPTION
                   "Indicates whether the blade owns the Media Tray.
                   0 = false, 1 = true."
                   ::= { bladeSystemStatusEntry 12 }

       bladeRemoteWakeOnLanEnable  OBJECT-TYPE
                   SYNTAX  INTEGER {
                     disabled(0),
                     enabled(1),
                     notApplicable(255)
                   }
                   MAX-ACCESS  read-only
                   STATUS  current -- was mandatory
                   DESCRIPTION
                   "Remote wake on LAN state for the blade.
                   0x01 indicates enabled."
                   ::= { bladeSystemStatusEntry 13 }

       bladeServerExpansion  OBJECT-TYPE
                   SYNTAX  INTEGER {
                     no(0),
                     yes(1)
                   }
                   MAX-ACCESS  read-only
                   STATUS  current -- was mandatory
                   DESCRIPTION
                   "This shows whether this blade has an expansion board attached. 
                   A yes column indicates that an expansion board is installed for this 
                   blade."
                   ::= { bladeSystemStatusEntry 14 }

       bladeWidth  OBJECT-TYPE
                   SYNTAX  INTEGER
                   MAX-ACCESS  read-only
                   STATUS  current -- was mandatory
                   DESCRIPTION
                   "The width of the blade including any supplement blade attached to it" 
                   ::= { bladeSystemStatusEntry 15 }

       bladeSupportCapacityOnDemand  OBJECT-TYPE
                   SYNTAX  INTEGER {
                     no(0),
                     yes(1)
                   }
                   MAX-ACCESS  read-only
                   STATUS  deprecated
                   DESCRIPTION
                   "This shows whether this blade support Capacity On Demand.
                    NOTE: This Mib object is deprecated and no longer supported." 
                   ::= { bladeSystemStatusEntry 16 }
       
       bladeServerExpansion2  OBJECT-TYPE
                   SYNTAX  INTEGER {
                     no(0),
                     yes(1)
                   }
                   MAX-ACCESS  read-only
                   STATUS  current -- was mandatory
                   DESCRIPTION
                   "This shows whether this blade has an expansion board attached. 
                   A yes column indicates that an expansion board is installed for this 
                   blade."
                   ::= { bladeSystemStatusEntry 17 }
       
       bladecKVMStatus  OBJECT-TYPE
                   SYNTAX  INTEGER {
                     notPresent(0),
                     notReady(1),
                     ready(2),
                     active(3),
                     disabled(4),
                     notAvailable(255)
                   }
                   MAX-ACCESS  read-only
                   STATUS  current -- was mandatory
                   DESCRIPTION
                   "This shows whether this blade has a concurrent keyboard, video, and 
                   mouse (cKVM) card installed and the status of cKVM on the blade.
                   
                   Not present: A cKVM card is not installed.
                   Not ready: A cKVM card is installed but is not functional. 
                   Ready: A cKVM card is installed and is functional, with no cKVM session in progress.
                   Active: A cKVM card is installed and is functional, with a cKVM session currently in progress.
                   Disabled: A cKVM card is not enabled on this blade.
                   Not available: A cKVM card is installed but the status is not available."
                   ::= { bladeSystemStatusEntry 21 }
       
       bladeConnectionType2  OBJECT-TYPE
                   SYNTAX  INTEGER {
                     none(0),
                     ethernet(1),
                     fiber(2),
                     serial(3), 
                     opticalPassThrough(4),
                     infiniband(5), 
                     iSCSI(6)
                   }
                   MAX-ACCESS  read-only
                   STATUS  current -- was mandatory
                   DESCRIPTION
                   "Connection type of the expansion card number 2."
                   ::= { bladeSystemStatusEntry 22 }
       
       bladeConnectionType3  OBJECT-TYPE
                   SYNTAX  INTEGER {
                     none(0),
                     ethernet(1),
                     fiber(2),
                     serial(3), 
                     opticalPassThrough(4),
                     infiniband(5), 
                     iSCSI(6)
                   }
                   MAX-ACCESS  read-only
                   STATUS  current -- was mandatory
                   DESCRIPTION
                   "Connection type of the expansion card number 3."
                   ::= { bladeSystemStatusEntry 23 }
                   
       bladeConnectionType4  OBJECT-TYPE
                   SYNTAX  INTEGER {
                     none(0),
                     ethernet(1),
                     fiber(2),
                     serial(3), 
                     opticalPassThrough(4),
                     infiniband(5), 
                     iSCSI(6)
                   }
                   MAX-ACCESS  read-only
                   STATUS  current -- was mandatory
                   DESCRIPTION
                   "Connection type of the expansion card number 4."
                   ::= { bladeSystemStatusEntry 24 }
                   
       bladeConnectionType5  OBJECT-TYPE
                   SYNTAX  INTEGER {
                     none(0),
                     ethernet(1),
                     fiber(2),
                     serial(3), 
                     opticalPassThrough(4),
                     infiniband(5), 
                     iSCSI(6)
                   }
                   MAX-ACCESS  read-only
                   STATUS  current -- was mandatory
                   DESCRIPTION
                   "Connection type of the expansion card number 5."
                   ::= { bladeSystemStatusEntry 25 }
       
       bladeHighSpeedConnectionType OBJECT-TYPE
                   SYNTAX  INTEGER {
                     none(0),
                     ethernet(1),
                     fiber(2),
                     serial(3), 
                     opticalPassThrough(4),
                     infiniband(5), 
                     iSCSI(6),
                     infinibandPassThrough(7)
                   }
                   MAX-ACCESS  read-only
                   STATUS  current -- was mandatory
                   DESCRIPTION
                   "Connection type of the high speed expansion card number 1."
                   ::= { bladeSystemStatusEntry 41 }
       
      bladeHealthSummaryTable OBJECT-TYPE
                    SYNTAX  SEQUENCE OF BladeHealthSummaryEntry
                    MAX-ACCESS  not-accessible
                    STATUS  current -- was mandatory
                    DESCRIPTION
                    "Table of blade health summary information.
                    Contains information about the overall blade health status."
                    ::= { bladeMonitors 2 }

      bladeHealthSummaryEntry OBJECT-TYPE
                    SYNTAX BladeHealthSummaryEntry
                    MAX-ACCESS  not-accessible
                    STATUS  current -- was mandatory
                    DESCRIPTION
                    "Blade health summary entry"
                    INDEX { bladeHealthSummaryIndex }
                    ::= { bladeHealthSummaryTable 1 }


      BladeHealthSummaryEntry ::= SEQUENCE {
                  bladeHealthSummaryIndex INTEGER,
                  bladeHealthSummaryBladeId INTEGER,
                  bladeHealthSummarySeverity OCTET STRING,
                  bladeHealthSummaryDescription OCTET STRING
                  }


      bladeHealthSummaryIndex  OBJECT-TYPE
                  SYNTAX  Integer32 (0..2147483647) -- was INTEGER
                  MAX-ACCESS  read-only
                  STATUS  current -- was mandatory
                  DESCRIPTION
                  "Blade health summary index."
                  ::= { bladeHealthSummaryEntry 1 }

       bladeHealthSummaryBladeId OBJECT-TYPE
                   SYNTAX  INTEGER {
                       blade1(1),
                       blade2(2),
                       blade3(3),
                       blade4(4),
                       blade5(5),
                       blade6(6),
                       blade7(7),
                       blade8(8),
                       blade9(9),
                       blade10(10),
                       blade11(11),
                       blade12(12),
                       blade13(13),
                       blade14(14)
                     }
                   MAX-ACCESS  read-only
                   STATUS  current -- was mandatory
                   DESCRIPTION
                   "The numeric blade ID."
                   ::= { bladeHealthSummaryEntry 2 }

      bladeHealthSummarySeverity  OBJECT-TYPE
                  SYNTAX  OCTET STRING
                  MAX-ACCESS  read-only
                  STATUS  current -- was mandatory
                  DESCRIPTION
                  "System health summary severity."
                  ::= { bladeHealthSummaryEntry 3 }

      bladeHealthSummaryDescription  OBJECT-TYPE
                  SYNTAX  OCTET STRING
                  MAX-ACCESS  read-only
                  STATUS  current -- was mandatory
                  DESCRIPTION
                  "System health summary description."
                  ::= { bladeHealthSummaryEntry 4 }



      bladeTemperaturesTable OBJECT-TYPE
                     SYNTAX  SEQUENCE OF BladeTemperaturesEntry
                     MAX-ACCESS  not-accessible
                     STATUS  current -- was mandatory
                     DESCRIPTION
                     "Table of blade temperatures information."
                     ::= { bladeMonitors 3 }

       bladeTemperaturesEntry OBJECT-TYPE
                     SYNTAX BladeTemperaturesEntry
                     MAX-ACCESS  not-accessible
                     STATUS  current -- was mandatory
                     DESCRIPTION
                     "Blade temperatures table entry"
                     INDEX { temperatureIndex }
                     ::= { bladeTemperaturesTable 1 }


       BladeTemperaturesEntry ::= SEQUENCE {
                   temperatureIndex INTEGER,
                   temperatureBladeId INTEGER,
                   temperatureBladeExists INTEGER,
                   temperatureBladePowerState INTEGER,
                   temperatureBladeName OCTET STRING,
                   temperatureCPU1 OCTET STRING,
                   temperatureCPU2 OCTET STRING,
                   temperatureCPU3 OCTET STRING,
                   temperatureCPU4 OCTET STRING,
                   temperatureDASD1 OCTET STRING,
                   bladeSensorTempCapability INTEGER,
                   bladeSensor1Temp OCTET STRING,
                   bladeSensor2Temp OCTET STRING,
                   bladeSensor3Temp OCTET STRING,
                   bladeSensor4Temp OCTET STRING,
                   bladeSensor5Temp OCTET STRING,
                   bladeSensor6Temp OCTET STRING,
                   bladeSensor7Temp OCTET STRING,
                   bladeSensor8Temp OCTET STRING,
                   bladeSensor9Temp OCTET STRING
                   }

       temperatureIndex  OBJECT-TYPE
                   SYNTAX  Integer32 (0..2147483647) -- was INTEGER
                   MAX-ACCESS  read-only
                   STATUS  current -- was mandatory
                   DESCRIPTION
                   "Blade temperatures table index."
                   ::= { bladeTemperaturesEntry 1 }


       temperatureBladeId  OBJECT-TYPE
                   SYNTAX  INTEGER {
                     blade1(1),
                     blade2(2),
                     blade3(3),
                     blade4(4),
                     blade5(5),
                     blade6(6),
                     blade7(7),
                     blade8(8),
                     blade9(9),
                     blade10(10),
                     blade11(11),
                     blade12(12),
                     blade13(13),
                     blade14(14)
                   }
                   MAX-ACCESS  read-only
                   STATUS  current -- was mandatory
                   DESCRIPTION
                   "The numeric blade ID."
                   ::= { bladeTemperaturesEntry 2 }

       temperatureBladeExists OBJECT-TYPE
                   SYNTAX  INTEGER {
                     false(0),
                     true(1)
                   }
                   MAX-ACCESS  read-only
                   STATUS  current -- was mandatory
                   DESCRIPTION
                   "Indicates whether the server blade specified exists or not."
                   ::= { bladeTemperaturesEntry 3 }

       temperatureBladePowerState OBJECT-TYPE
                   SYNTAX  INTEGER {
                     off(0),
                     on(1),
                     standby(3),
                     hibernate(4)                     
                   }
                   MAX-ACCESS  read-only
                   STATUS  current -- was mandatory
                   DESCRIPTION
                   "Indicates the power state of the blade specified."
                   ::= { bladeTemperaturesEntry 4 }

       temperatureBladeName OBJECT-TYPE
                   SYNTAX  OCTET STRING
                   MAX-ACCESS  read-only
                   STATUS  current -- was mandatory
                   DESCRIPTION
                   "The name of the blade as a null terminated string."
                   ::= { bladeTemperaturesEntry 5 }

       temperatureCPU1 OBJECT-TYPE
                   SYNTAX  OCTET STRING
                   MAX-ACCESS  read-only
                   STATUS  current -- was mandatory
                   DESCRIPTION
                   "The blade CPU temperature in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperaturesEntry 6 }

       temperatureCPU2 OBJECT-TYPE
                   SYNTAX  OCTET STRING
                   MAX-ACCESS  read-only
                   STATUS  current -- was mandatory
                   DESCRIPTION
                   "The blade CPU temperature in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperaturesEntry 7 }

       temperatureCPU3 OBJECT-TYPE
                   SYNTAX  OCTET STRING
                   MAX-ACCESS  read-only
                   STATUS  current -- was mandatory
                   DESCRIPTION
                   "The blade CPU temperature in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperaturesEntry 8 }

       temperatureCPU4 OBJECT-TYPE
                   SYNTAX  OCTET STRING
                   MAX-ACCESS  read-only
                   STATUS  current -- was mandatory
                   DESCRIPTION
                   "The blade CPU temperature in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperaturesEntry 9 }

       temperatureDASD1 OBJECT-TYPE
                   SYNTAX  OCTET STRING
                   MAX-ACCESS  read-only
                   STATUS  current -- was mandatory
                   DESCRIPTION
                   "The blade DASD temperature in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperaturesEntry 10 }
                   
       bladeSensorTempCapability OBJECT-TYPE
                   SYNTAX  INTEGER {
                     false(0),
                     true(1)
                   }
                   MAX-ACCESS  read-only
                   STATUS  current -- was mandatory
                   DESCRIPTION
                   "Indicates whether the server blade is IPMI capable or not."
                   ::= { bladeTemperaturesEntry 11 }                   
                   
       bladeSensor1Temp OBJECT-TYPE
                   SYNTAX  OCTET STRING
                   MAX-ACCESS  read-only
                   STATUS  current -- was mandatory
                   DESCRIPTION
                   "Temperature reading for an IPMI blade expressed in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperaturesEntry 12 }

       bladeSensor2Temp OBJECT-TYPE
                   SYNTAX  OCTET STRING
                   MAX-ACCESS  read-only
                   STATUS  current -- was mandatory
                   DESCRIPTION
                   "Temperature reading for an IPMI blade expressed in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperaturesEntry 13 }

       bladeSensor3Temp OBJECT-TYPE
                   SYNTAX  OCTET STRING
                   MAX-ACCESS  read-only
                   STATUS  current -- was mandatory
                   DESCRIPTION
                   "Temperature reading for an IPMI blade expressed in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperaturesEntry 14 }

       bladeSensor4Temp OBJECT-TYPE
                   SYNTAX  OCTET STRING
                   MAX-ACCESS  read-only
                   STATUS  current -- was mandatory
                   DESCRIPTION
                   "Temperature reading for an IPMI blade expressed in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperaturesEntry 15 }

       bladeSensor5Temp OBJECT-TYPE
                   SYNTAX  OCTET STRING
                   MAX-ACCESS  read-only
                   STATUS  current -- was mandatory
                   DESCRIPTION
                   "Temperature reading for an IPMI blade expressed in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperaturesEntry 16 }

       bladeSensor6Temp OBJECT-TYPE
                   SYNTAX  OCTET STRING
                   MAX-ACCESS  read-only
                   STATUS  current -- was mandatory
                   DESCRIPTION
                   "Temperature reading for an IPMI blade expressed in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperaturesEntry 17 }

       bladeSensor7Temp OBJECT-TYPE
                   SYNTAX  OCTET STRING
                   MAX-ACCESS  read-only
                   STATUS  current -- was mandatory
                   DESCRIPTION
                   "Temperature reading for an IPMI blade expressed in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperaturesEntry 18 }

       bladeSensor8Temp OBJECT-TYPE
                   SYNTAX  OCTET STRING
                   MAX-ACCESS  read-only
                   STATUS  current -- was mandatory
                   DESCRIPTION
                   "Temperature reading for an IPMI blade expressed in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperaturesEntry 19 }
                   
        bladeSensor9Temp OBJECT-TYPE
                   SYNTAX  OCTET STRING
                   MAX-ACCESS  read-only
                   STATUS  current -- was mandatory
                   DESCRIPTION
                   "Temperature reading for an IPMI blade expressed in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperaturesEntry 20 }

      bladeTemperatureThresholdsTable OBJECT-TYPE
                     SYNTAX  SEQUENCE OF BladeTemperatureThresholdsEntry
                     MAX-ACCESS  not-accessible
                     STATUS  current -- was mandatory
                     DESCRIPTION
                     "Table of blade temperature thresholds information."
                     ::= { bladeMonitors 4 }

       bladeTemperatureThresholdsEntry OBJECT-TYPE
                     SYNTAX BladeTemperatureThresholdsEntry
                     MAX-ACCESS  not-accessible
                     STATUS  current -- was mandatory
                     DESCRIPTION
                     "Blade temperature thresholds table entry"
                     INDEX { temperatureThresholdIndex }
                     ::= { bladeTemperatureThresholdsTable 1 }


       BladeTemperatureThresholdsEntry ::= SEQUENCE {
                   temperatureThresholdIndex INTEGER,
                   temperatureThresholdBladeId INTEGER,
                   temperatureThresholdBladeExists INTEGER,
                   temperatureThresholdBladePowerState INTEGER,
                   temperatureThresholdBladeName OCTET STRING,
                   temperatureCPU1HardShutdown OCTET STRING,
                   temperatureCPU1Warning OCTET STRING,
                   temperatureCPU1WarningReset OCTET STRING,
                   temperatureCPU2HardShutdown OCTET STRING,
                   temperatureCPU2Warning OCTET STRING,
                   temperatureCPU2WarningReset OCTET STRING,
                   temperatureCPU3HardShutdown OCTET STRING,
                   temperatureCPU3Warning OCTET STRING,
                   temperatureCPU3WarningReset OCTET STRING,
                   temperatureCPU4HardShutdown OCTET STRING,
                   temperatureCPU4Warning OCTET STRING,
                   temperatureCPU4WarningReset OCTET STRING,
                   temperatureDASD1HardShutdown OCTET STRING,
                   temperatureDASD1Warning OCTET STRING,
                   temperatureDASD1WarningReset OCTET STRING,
                   bladeTempThresholdSensorCapability INTEGER,
                   temperatureSensor1HardShutdown OCTET STRING,
                   temperatureSensor1Warning OCTET STRING,
                   temperatureSensor1WarningReset OCTET STRING,
                   temperatureSensor2HardShutdown OCTET STRING,
                   temperatureSensor2Warning OCTET STRING,
                   temperatureSensor2WarningReset OCTET STRING,
                   temperatureSensor3HardShutdown OCTET STRING,
                   temperatureSensor3Warning OCTET STRING,
                   temperatureSensor3WarningReset OCTET STRING,
                   temperatureSensor4HardShutdown OCTET STRING,
                   temperatureSensor4Warning OCTET STRING,
                   temperatureSensor4WarningReset OCTET STRING,
                   temperatureSensor5HardShutdown OCTET STRING,
                   temperatureSensor5Warning OCTET STRING,
                   temperatureSensor5WarningReset OCTET STRING,
                   temperatureSensor6HardShutdown OCTET STRING,
                   temperatureSensor6Warning OCTET STRING,
                   temperatureSensor6WarningReset OCTET STRING,
                   temperatureSensor7HardShutdown OCTET STRING,
                   temperatureSensor7Warning OCTET STRING,
                   temperatureSensor7WarningReset OCTET STRING,
                   temperatureSensor8HardShutdown OCTET STRING,
                   temperatureSensor8Warning OCTET STRING,
                   temperatureSensor8WarningReset OCTET STRING,
                   temperatureSensor9HardShutdown OCTET STRING,
                   temperatureSensor9Warning OCTET STRING,
                   temperatureSensor9WarningReset OCTET STRING
                   }

       temperatureThresholdIndex  OBJECT-TYPE
                   SYNTAX  Integer32 (0..2147483647) -- was INTEGER
                   MAX-ACCESS  read-only
                   STATUS  current -- was mandatory
                   DESCRIPTION
                   "Blade temperature threshold table index."
                   ::= { bladeTemperatureThresholdsEntry 1 }


       temperatureThresholdBladeId  OBJECT-TYPE
                   SYNTAX  INTEGER {
                     blade1(1),
                     blade2(2),
                     blade3(3),
                     blade4(4),
                     blade5(5),
                     blade6(6),
                     blade7(7),
                     blade8(8),
                     blade9(9),
                     blade10(10),
                     blade11(11),
                     blade12(12),
                     blade13(13),
                     blade14(14)
                   }
                   MAX-ACCESS  read-only
                   STATUS  current -- was mandatory
                   DESCRIPTION
                   "The numeric blade ID."
                   ::= { bladeTemperatureThresholdsEntry 2 }

       temperatureThresholdBladeExists OBJECT-TYPE
                   SYNTAX  INTEGER {
                     false(0),
                     true(1)
                   }
                   MAX-ACCESS  read-only
                   STATUS  current -- was mandatory
                   DESCRIPTION
                   "Indicates whether the server blade specified exists or not."
                   ::= { bladeTemperatureThresholdsEntry 3 }

       temperatureThresholdBladePowerState OBJECT-TYPE
                   SYNTAX  INTEGER {
                     off(0),
                     on(1),
                     standby(3),
                     hibernate(4)                     
                   }
                   MAX-ACCESS  read-only
                   STATUS  current -- was mandatory
                   DESCRIPTION
                   "Indicates the power state of the blade specified."
                   ::= { bladeTemperatureThresholdsEntry 4 }

       temperatureThresholdBladeName OBJECT-TYPE
                   SYNTAX  OCTET STRING
                   MAX-ACCESS  read-only
                   STATUS  current -- was mandatory
                   DESCRIPTION
                   "The name of the blade as a null terminated string."
                   ::= { bladeTemperatureThresholdsEntry 5 }

       temperatureCPU1HardShutdown OBJECT-TYPE
                   SYNTAX  OCTET STRING
                   MAX-ACCESS  read-only
                   STATUS  current -- was mandatory
                   DESCRIPTION
                   "The blade CPU hard shutdown temperature in degrees
                   centigrade(C).  If the component's temperature rises above
                   this value the system will be powered off immediately.
                   If enabled, a critical alert/event will be generated.
                   An octet string expressed as 'sddd.dd Centigrade' where:
                   s is the sign ('-' for negative or blank space for positive)
                   d is a decimal digit or blank space for a leading zero.
                   The string 'Not Readable!' indicates that the given monitor
                   is not supported on this system.
                   The string 'No Temperature' indicates that the given monitor
                   does not exist on this system or is powered off."
                   ::= { bladeTemperatureThresholdsEntry 6 }

       temperatureCPU1Warning OBJECT-TYPE
                   SYNTAX  OCTET STRING
                   MAX-ACCESS  read-only
                   STATUS  current -- was mandatory
                   DESCRIPTION
                   "The blade CPU warning temperature in degrees centigrade(C).
                   If the temperature rises above this value a warning alert/event
                   if enabled will be generated.
                   An octet string expressed as 'sddd.dd Centigrade' where:
                   s is the sign ('-' for negative or blank space for positive)
                   d is a decimal digit or blank space for a leading zero.
                   The string 'Not Readable!' indicates that the given monitor
                   is not supported on this system.
                   The string 'No Temperature' indicates that the given monitor
                   does not exist on this system or is powered off."
                   ::= { bladeTemperatureThresholdsEntry 7 }

       temperatureCPU1WarningReset OBJECT-TYPE
                   SYNTAX  OCTET STRING
                   MAX-ACCESS  read-only
                   STATUS  current -- was mandatory
                   DESCRIPTION
                   "The blade CPU warning reset temperature in degrees
                   centigrade(C).  If the temperature rises above this value and
                   if a warning alert/event had previously been created then the
                   alert/event will be reset.
                   An octet string expressed as 'sddd.dd Centigrade' where:
                   s is the sign ('-' for negative or blank space for positive)
                   d is a decimal digit or blank space for a leading zero.
                   The string 'Not Readable!' indicates that the given monitor
                   is not supported on this system.
                   The string 'No Temperature' indicates that the given monitor
                   does not exist on this system or is powered off."
                   ::= { bladeTemperatureThresholdsEntry 8 }

       temperatureCPU2HardShutdown OBJECT-TYPE
                   SYNTAX  OCTET STRING
                   MAX-ACCESS  read-only
                   STATUS  current -- was mandatory
                   DESCRIPTION
                   "The blade CPU hard shutdown temperature in degrees
                   centigrade(C).  If the component's temperature rises above
                   this value the system will be powered off immediately.
                   If enabled, a critical alert/event will be generated.
                   An octet string expressed as 'sddd.dd Centigrade' where:
                   s is the sign ('-' for negative or blank space for positive)
                   d is a decimal digit or blank space for a leading zero.
                   The string 'Not Readable!' indicates that the given monitor
                   is not supported on this system.
                   The string 'No Temperature' indicates that the given monitor
                   does not exist on this system or is powered off."
                   ::= { bladeTemperatureThresholdsEntry 9 }

       temperatureCPU2Warning OBJECT-TYPE
                   SYNTAX  OCTET STRING
                   MAX-ACCESS  read-only
                   STATUS  current -- was mandatory
                   DESCRIPTION
                   "The blade CPU warning temperature in degrees centigrade(C).
                   If the temperature rises above this value a warning alert/event
                   if enabled will be generated.
                   An octet string expressed as 'sddd.dd Centigrade' where:
                   s is the sign ('-' for negative or blank space for positive)
                   d is a decimal digit or blank space for a leading zero.
                   The string 'Not Readable!' indicates that the given monitor
                   is not supported on this system.
                   The string 'No Temperature' indicates that the given monitor
                   does not exist on this system or is powered off."
                   ::= { bladeTemperatureThresholdsEntry 10 }

       temperatureCPU2WarningReset OBJECT-TYPE
                   SYNTAX  OCTET STRING
                   MAX-ACCESS  read-only
                   STATUS  current -- was mandatory
                   DESCRIPTION
                   "The blade CPU warning reset temperature in degrees
                   centigrade(C).  If the temperature rises above this value and
                   if a warning alert/event had previously been created then the
                   alert/event will be reset.
                   An octet string expressed as 'sddd.dd Centigrade' where:
                   s is the sign ('-' for negative or blank space for positive)
                   d is a decimal digit or blank space for a leading zero.
                   The string 'Not Readable!' indicates that the given monitor
                   is not supported on this system.
                   The string 'No Temperature' indicates that the given monitor
                   does not exist on this system or is powered off."
                   ::= { bladeTemperatureThresholdsEntry 11 }

       temperatureCPU3HardShutdown OBJECT-TYPE
                   SYNTAX  OCTET STRING
                   MAX-ACCESS  read-only
                   STATUS  current -- was mandatory
                   DESCRIPTION
                   "The blade CPU hard shutdown temperature in degrees
                   centigrade(C).  If the component's temperature rises above
                   this value the system will be powered off immediately.
                   If enabled, a critical alert/event will be generated.
                   An octet string expressed as 'sddd.dd Centigrade' where:
                   s is the sign ('-' for negative or blank space for positive)
                   d is a decimal digit or blank space for a leading zero.
                   The string 'Not Readable!' indicates that the given monitor
                   is not supported on this system.
                   The string 'No Temperature' indicates that the given monitor
                   does not exist on this system or is powered off."
                   ::= { bladeTemperatureThresholdsEntry 12 }

       temperatureCPU3Warning OBJECT-TYPE
                   SYNTAX  OCTET STRING
                   MAX-ACCESS  read-only
                   STATUS  current -- was mandatory
                   DESCRIPTION
                   "The blade CPU warning temperature in degrees centigrade(C).
                   If the temperature rises above this value a warning alert/event
                   if enabled will be generated.
                   An octet string expressed as 'sddd.dd Centigrade' where:
                   s is the sign ('-' for negative or blank space for positive)
                   d is a decimal digit or blank space for a leading zero.
                   The string 'Not Readable!' indicates that the given monitor
                   is not supported on this system.
                   The string 'No Temperature' indicates that the given monitor
                   does not exist on this system or is powered off."
                   ::= { bladeTemperatureThresholdsEntry 13 }

       temperatureCPU3WarningReset OBJECT-TYPE
                   SYNTAX  OCTET STRING
                   MAX-ACCESS  read-only
                   STATUS  current -- was mandatory
                   DESCRIPTION
                   "The blade CPU warning reset temperature in degrees
                   centigrade(C).  If the temperature rises above this value and
                   if a warning alert/event had previously been created then the
                   alert/event will be reset.
                   An octet string expressed as 'sddd.dd Centigrade' where:
                   s is the sign ('-' for negative or blank space for positive)
                   d is a decimal digit or blank space for a leading zero.
                   The string 'Not Readable!' indicates that the given monitor
                   is not supported on this system.
                   The string 'No Temperature' indicates that the given monitor
                   does not exist on this system or is powered off."
                   ::= { bladeTemperatureThresholdsEntry 14 }

       temperatureCPU4HardShutdown OBJECT-TYPE
                   SYNTAX  OCTET STRING
                   MAX-ACCESS  read-only
                   STATUS  current -- was mandatory
                   DESCRIPTION
                   "The blade CPU hard shutdown temperature in degrees
                   centigrade(C).  If the component's temperature rises above
                   this value the system will be powered off immediately.
                   If enabled, a critical alert/event will be generated.
                   An octet string expressed as 'sddd.dd Centigrade' where:
                   s is the sign ('-' for negative or blank space for positive)
                   d is a decimal digit or blank space for a leading zero.
                   The string 'Not Readable!' indicates that the given monitor
                   is not supported on this system.
                   The string 'No Temperature' indicates that the given monitor
                   does not exist on this system or is powered off."
                   ::= { bladeTemperatureThresholdsEntry 15 }

       temperatureCPU4Warning OBJECT-TYPE
                   SYNTAX  OCTET STRING
                   MAX-ACCESS  read-only
                   STATUS  current -- was mandatory
                   DESCRIPTION
                   "The blade CPU warning temperature in degrees centigrade(C).
                   If the temperature rises above this value a warning alert/event
                   if enabled will be generated.
                   An octet string expressed as 'sddd.dd Centigrade' where:
                   s is the sign ('-' for negative or blank space for positive)
                   d is a decimal digit or blank space for a leading zero.
                   The string 'Not Readable!' indicates that the given monitor
                   is not supported on this system.
                   The string 'No Temperature' indicates that the given monitor
                   does not exist on this system or is powered off."
                   ::= { bladeTemperatureThresholdsEntry 16 }

       temperatureCPU4WarningReset OBJECT-TYPE
                   SYNTAX  OCTET STRING
                   MAX-ACCESS  read-only
                   STATUS  current -- was mandatory
                   DESCRIPTION
                   "The blade CPU warning reset temperature in degrees
                   centigrade(C).  If the temperature rises above this value and
                   if a warning alert/event had previously been created then the
                   alert/event will be reset.
                   An octet string expressed as 'sddd.dd Centigrade' where:
                   s is the sign ('-' for negative or blank space for positive)
                   d is a decimal digit or blank space for a leading zero.
                   The string 'Not Readable!' indicates that the given monitor
                   is not supported on this system.
                   The string 'No Temperature' indicates that the given monitor
                   does not exist on this system or is powered off."
                   ::= { bladeTemperatureThresholdsEntry 17 }

       temperatureDASD1HardShutdown OBJECT-TYPE
                   SYNTAX  OCTET STRING
                   MAX-ACCESS  read-only
                   STATUS  current -- was mandatory
                   DESCRIPTION
                   "The blade DASD hard shutdown temperature in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 18 }

       temperatureDASD1Warning OBJECT-TYPE
                   SYNTAX  OCTET STRING
                   MAX-ACCESS  read-only
                   STATUS  current -- was mandatory
                   DESCRIPTION
                   "The blade DASD warning temperature in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 19 }

       temperatureDASD1WarningReset OBJECT-TYPE
                   SYNTAX  OCTET STRING
                   MAX-ACCESS  read-only
                   STATUS  current -- was mandatory
                   DESCRIPTION
                   "The blade DASD warning reset temperature in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 20 }
                   
       bladeTempThresholdSensorCapability OBJECT-TYPE
                   SYNTAX  INTEGER {
                     false(0),
                     true(1)
                   }
                   MAX-ACCESS  read-only
                   STATUS  current -- was mandatory
                   DESCRIPTION
                   "Indicates whether the server blade is IPMI capable or not."
                   ::= { bladeTemperatureThresholdsEntry 21 }

       temperatureSensor1HardShutdown OBJECT-TYPE
                   SYNTAX  OCTET STRING
                   MAX-ACCESS  read-only
                   STATUS  current -- was mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 22 }

       temperatureSensor1Warning OBJECT-TYPE
                   SYNTAX  OCTET STRING
                   MAX-ACCESS  read-only
                   STATUS  current -- was mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 23 }

       temperatureSensor1WarningReset OBJECT-TYPE
                   SYNTAX  OCTET STRING
                   MAX-ACCESS  read-only
                   STATUS  current -- was mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 24 }

       temperatureSensor2HardShutdown OBJECT-TYPE
                   SYNTAX  OCTET STRING
                   MAX-ACCESS  read-only
                   STATUS  current -- was mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 25 }

       temperatureSensor2Warning OBJECT-TYPE
                   SYNTAX  OCTET STRING
                   MAX-ACCESS  read-only
                   STATUS  current -- was mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 26 }

       temperatureSensor2WarningReset OBJECT-TYPE
                   SYNTAX  OCTET STRING
                   MAX-ACCESS  read-only
                   STATUS  current -- was mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 27 }

       temperatureSensor3HardShutdown OBJECT-TYPE
                   SYNTAX  OCTET STRING
                   MAX-ACCESS  read-only
                   STATUS  current -- was mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 28 }

       temperatureSensor3Warning OBJECT-TYPE
                   SYNTAX  OCTET STRING
                   MAX-ACCESS  read-only
                   STATUS  current -- was mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 29 }

       temperatureSensor3WarningReset OBJECT-TYPE
                   SYNTAX  OCTET STRING
                   MAX-ACCESS  read-only
                   STATUS  current -- was mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 30 }

       temperatureSensor4HardShutdown OBJECT-TYPE
                   SYNTAX  OCTET STRING
                   MAX-ACCESS  read-only
                   STATUS  current -- was mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 31 }

       temperatureSensor4Warning OBJECT-TYPE
                   SYNTAX  OCTET STRING
                   MAX-ACCESS  read-only
                   STATUS  current -- was mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 32 }

       temperatureSensor4WarningReset OBJECT-TYPE
                   SYNTAX  OCTET STRING
                   MAX-ACCESS  read-only
                   STATUS  current -- was mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 33 }

       temperatureSensor5HardShutdown OBJECT-TYPE
                   SYNTAX  OCTET STRING
                   MAX-ACCESS  read-only
                   STATUS  current -- was mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 34 }

       temperatureSensor5Warning OBJECT-TYPE
                   SYNTAX  OCTET STRING
                   MAX-ACCESS  read-only
                   STATUS  current -- was mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 35 }

       temperatureSensor5WarningReset OBJECT-TYPE
                   SYNTAX  OCTET STRING
                   MAX-ACCESS  read-only
                   STATUS  current -- was mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 36 }

       temperatureSensor6HardShutdown OBJECT-TYPE
                   SYNTAX  OCTET STRING
                   MAX-ACCESS  read-only
                   STATUS  current -- was mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 37 }

       temperatureSensor6Warning OBJECT-TYPE
                   SYNTAX  OCTET STRING
                   MAX-ACCESS  read-only
                   STATUS  current -- was mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 38 }

       temperatureSensor6WarningReset OBJECT-TYPE
                   SYNTAX  OCTET STRING
                   MAX-ACCESS  read-only
                   STATUS  current -- was mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 39 }

       temperatureSensor7HardShutdown OBJECT-TYPE
                   SYNTAX  OCTET STRING
                   MAX-ACCESS  read-only
                   STATUS  current -- was mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 40 }

       temperatureSensor7Warning OBJECT-TYPE
                   SYNTAX  OCTET STRING
                   MAX-ACCESS  read-only
                   STATUS  current -- was mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 41 }

       temperatureSensor7WarningReset OBJECT-TYPE
                   SYNTAX  OCTET STRING
                   MAX-ACCESS  read-only
                   STATUS  current -- was mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 42 }

       temperatureSensor8HardShutdown OBJECT-TYPE
                   SYNTAX  OCTET STRING
                   MAX-ACCESS  read-only
                   STATUS  current -- was mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 43 }

       temperatureSensor8Warning OBJECT-TYPE
                   SYNTAX  OCTET STRING
                   MAX-ACCESS  read-only
                   STATUS  current -- was mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 44 }

       temperatureSensor8WarningReset OBJECT-TYPE
                   SYNTAX  OCTET STRING
                   MAX-ACCESS  read-only
                   STATUS  current -- was mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 45 }

       temperatureSensor9HardShutdown OBJECT-TYPE
                   SYNTAX  OCTET STRING
                   MAX-ACCESS  read-only
                   STATUS  current -- was mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 46 }

       temperatureSensor9Warning OBJECT-TYPE
                   SYNTAX  OCTET STRING
                   MAX-ACCESS  read-only
                   STATUS  current -- was mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 47 }

       temperatureSensor9WarningReset OBJECT-TYPE
                   SYNTAX  OCTET STRING
                   MAX-ACCESS  read-only
                   STATUS  current -- was mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 48 }



      bladeVoltagesTable OBJECT-TYPE
                     SYNTAX  SEQUENCE OF BladeVoltagesEntry
                     MAX-ACCESS  not-accessible
                     STATUS  current -- was mandatory
                     DESCRIPTION
                     "Table of blade voltages information."
                     ::= { bladeMonitors 5 }

       bladeVoltagesEntry OBJECT-TYPE
                     SYNTAX BladeVoltagesEntry
                     MAX-ACCESS  not-accessible
                     STATUS  current -- was mandatory
                     DESCRIPTION
                     "Blade voltages table entry"
                     INDEX { voltageIndex }
                     ::= { bladeVoltagesTable 1 }

       BladeVoltagesEntry ::= SEQUENCE {
                   voltageIndex INTEGER,
                   voltageBladeId INTEGER,
                   voltageBladeExists INTEGER,
                   voltageBladePowerState INTEGER,
                   voltageBladeName OCTET STRING,
                   bladePlus5Volt OCTET STRING,
                   bladePlus3pt3Volt OCTET STRING,
                   bladePlus12Volt OCTET STRING,
                   bladePlus2pt5Volt OCTET STRING,
                   bladePlus1pt5Volt OCTET STRING,
                   bladePlus1pt25Volt OCTET STRING,
                   bladeVRM1Volt OCTET STRING,
                   bladeSensorVoltCapability INTEGER,
                   bladeSensor1Volt OCTET STRING,
                   bladeSensor2Volt OCTET STRING,
                   bladeSensor3Volt OCTET STRING,
                   bladeSensor4Volt OCTET STRING,
                   bladeSensor5Volt OCTET STRING,
                   bladeSensor6Volt OCTET STRING,
                   bladeSensor7Volt OCTET STRING,
                   bladeSensor8Volt OCTET STRING,
                   bladeSensor9Volt OCTET STRING,
                   bladeSensor10Volt OCTET STRING,
                   bladeSensor11Volt OCTET STRING,
                   bladeSensor12Volt OCTET STRING,
                   bladeSensor13Volt OCTET STRING,
                   bladeSensor14Volt OCTET STRING,
                   bladeSensor15Volt OCTET STRING,
                   bladeSensor16Volt OCTET STRING,
                   bladeSensor17Volt OCTET STRING,
                   bladeSensor18Volt OCTET STRING,
                   bladeSensor19Volt OCTET STRING,
                   bladeSensor20Volt OCTET STRING,
                   bladeSensor21Volt OCTET STRING,
                   bladeSensor22Volt OCTET STRING,
                   bladeSensor23Volt OCTET STRING,
                   bladeSensor24Volt OCTET STRING,
                   bladeSensor25Volt OCTET STRING, 
                   bladeSensor26Volt OCTET STRING, 
                   bladeSensor27Volt OCTET STRING, 
                   bladeSensor28Volt OCTET STRING, 
                   bladeSensor29Volt OCTET STRING, 
                   bladeSensor30Volt OCTET STRING 
                   }

       voltageIndex  OBJECT-TYPE
                   SYNTAX  Integer32 (0..2147483647) -- was INTEGER
                   MAX-ACCESS  read-only
                   STATUS  current -- was mandatory
                   DESCRIPTION
                   "Blade voltages table index."
                   ::= { bladeVoltagesEntry 1 }


       voltageBladeId  OBJECT-TYPE
                   SYNTAX  INTEGER {
                     blade1(1),
                     blade2(2),
                     blade3(3),
                     blade4(4),
                     blade5(5),
                     blade6(6),
                     blade7(7),
                     blade8(8),
                     blade9(9),
                     blade10(10),
                     blade11(11),
                     blade12(12),
                     blade13(13),
                     blade14(14)
                   }
                   MAX-ACCESS  read-only
                   STATUS  current -- was mandatory
                   DESCRIPTION
                   "The numeric blade ID."
                   ::= { bladeVoltagesEntry 2 }

       voltageBladeExists OBJECT-TYPE
                   SYNTAX  INTEGER {
                     false(0),
                     true(1)
                   }
                   MAX-ACCESS  read-only
                   STATUS  current -- was mandatory
                   DESCRIPTION
                   "Indicates whether the server blade specified exists or not."
                   ::= { bladeVoltagesEntry 3 }

       voltageBladePowerState OBJECT-TYPE
                   SYNTAX  INTEGER {
                     off(0),
                     on(1),
                     standby(3),
                     hibernate(4)                     
                   }
                   MAX-ACCESS  read-only
                   STATUS  current -- was mandatory
                   DESCRIPTION
                   "Indicates the power state of the blade specified."
                   ::= { bladeVoltagesEntry 4 }

       voltageBladeName OBJECT-TYPE
                   SYNTAX  OCTET STRING
                   MAX-ACCESS  read-only
                   STATUS  current -- was mandatory
                   DESCRIPTION
                   "The name of the blade as a null terminated string."
                   ::= { bladeVoltagesEntry 5 }

       bladePlus5Volt OBJECT-TYPE
                   SYNTAX  OCTET STRING
                   MAX-ACCESS  read-only
                   STATUS  current -- was mandatory
                   DESCRIPTION
                   "+5 Volt power supply voltage reading for the blade
                   expressed in Volts(V).  An octet string expressed as
                   'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 6 }

       bladePlus3pt3Volt OBJECT-TYPE
                   SYNTAX  OCTET STRING
                   MAX-ACCESS  read-only
                   STATUS  current -- was mandatory
                   DESCRIPTION
                   "+3.3 Volt power supply voltage reading for the blade
                   expressed in Volts(V).  An octet string expressed as
                   'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 7 }

       bladePlus12Volt OBJECT-TYPE
                   SYNTAX  OCTET STRING
                   MAX-ACCESS  read-only
                   STATUS  current -- was mandatory
                   DESCRIPTION
                   "+12 Volt power supply voltage reading for the blade
                   expressed in Volts(V).  An octet string expressed as
                   'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 8 }

       bladePlus2pt5Volt OBJECT-TYPE
                   SYNTAX  OCTET STRING
                   MAX-ACCESS  read-only
                   STATUS  current -- was mandatory
                   DESCRIPTION
                   "+2.5 Volt power supply voltage reading for the blade
                   expressed in Volts(V).  An octet string expressed as
                   'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 10 }

       bladePlus1pt5Volt OBJECT-TYPE
                   SYNTAX  OCTET STRING
                   MAX-ACCESS  read-only
                   STATUS  current -- was mandatory
                   DESCRIPTION
                   "+1.5 Volt power supply voltage reading for the blade
                   expressed in Volts(V).  An octet string expressed as
                   'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 11 }

       bladePlus1pt25Volt OBJECT-TYPE
                   SYNTAX  OCTET STRING
                   MAX-ACCESS  read-only
                   STATUS  current -- was mandatory
                   DESCRIPTION
                   "+1.25 Volt power supply voltage reading for the blade
                   expressed in Volts(V).  An octet string expressed as
                   'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 12 }

       bladeVRM1Volt OBJECT-TYPE
                   SYNTAX  OCTET STRING
                   MAX-ACCESS  read-only
                   STATUS  current -- was mandatory
                   DESCRIPTION
                   "VRM 1 voltage reading for the blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 13 }

       bladeSensorVoltCapability OBJECT-TYPE
                   SYNTAX  INTEGER {
                     false(0),
                     true(1)
                   }
                   MAX-ACCESS  read-only
                   STATUS  current -- was mandatory
                   DESCRIPTION
                   "Indicates whether the server blade is IPMI capable or not."
                   ::= { bladeVoltagesEntry 14 }
                   
       bladeSensor1Volt OBJECT-TYPE
                   SYNTAX  OCTET STRING
                   MAX-ACCESS  read-only
                   STATUS  current -- was mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 15 }

       bladeSensor2Volt OBJECT-TYPE
                   SYNTAX  OCTET STRING
                   MAX-ACCESS  read-only
                   STATUS  current -- was mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 16 }

       bladeSensor3Volt OBJECT-TYPE
                   SYNTAX  OCTET STRING
                   MAX-ACCESS  read-only
                   STATUS  current -- was mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 17 }

       bladeSensor4Volt OBJECT-TYPE
                   SYNTAX  OCTET STRING
                   MAX-ACCESS  read-only
                   STATUS  current -- was mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 18 }

       bladeSensor5Volt OBJECT-TYPE
                   SYNTAX  OCTET STRING
                   MAX-ACCESS  read-only
                   STATUS  current -- was mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 19 }

       bladeSensor6Volt OBJECT-TYPE
                   SYNTAX  OCTET STRING
                   MAX-ACCESS  read-only
                   STATUS  current -- was mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 20 }

       bladeSensor7Volt OBJECT-TYPE
                   SYNTAX  OCTET STRING
                   MAX-ACCESS  read-only
                   STATUS  current -- was mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 21 }

       bladeSensor8Volt OBJECT-TYPE
                   SYNTAX  OCTET STRING
                   MAX-ACCESS  read-only
                   STATUS  current -- was mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 22 }

       bladeSensor9Volt OBJECT-TYPE
                   SYNTAX  OCTET STRING
                   MAX-ACCESS  read-only
                   STATUS  current -- was mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 23 }

       bladeSensor10Volt OBJECT-TYPE
                   SYNTAX  OCTET STRING
                   MAX-ACCESS  read-only
                   STATUS  current -- was mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 24 }

       bladeSensor11Volt OBJECT-TYPE
                   SYNTAX  OCTET STRING
                   MAX-ACCESS  read-only
                   STATUS  current -- was mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 25 }

       bladeSensor12Volt OBJECT-TYPE
                   SYNTAX  OCTET STRING
                   MAX-ACCESS  read-only
                   STATUS  current -- was mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 26 }

       bladeSensor13Volt OBJECT-TYPE
                   SYNTAX  OCTET STRING
                   MAX-ACCESS  read-only
                   STATUS  current -- was mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 27 }

       bladeSensor14Volt OBJECT-TYPE
                   SYNTAX  OCTET STRING
                   MAX-ACCESS  read-only
                   STATUS  current -- was mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 28 }

       bladeSensor15Volt OBJECT-TYPE
                   SYNTAX  OCTET STRING
                   MAX-ACCESS  read-only
                   STATUS  current -- was mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 29 }

       bladeSensor16Volt OBJECT-TYPE
                   SYNTAX  OCTET STRING
                   MAX-ACCESS  read-only
                   STATUS  current -- was mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 30 }

       bladeSensor17Volt OBJECT-TYPE
                   SYNTAX  OCTET STRING
                   MAX-ACCESS  read-only
                   STATUS  current -- was mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 31 }

       bladeSensor18Volt OBJECT-TYPE
                   SYNTAX  OCTET STRING
                   MAX-ACCESS  read-only
                   STATUS  current -- was mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 32 }

       bladeSensor19Volt OBJECT-TYPE
                   SYNTAX  OCTET STRING
                   MAX-ACCESS  read-only
                   STATUS  current -- was mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 33 }

       bladeSensor20Volt OBJECT-TYPE
                   SYNTAX  OCTET STRING
                   MAX-ACCESS  read-only
                   STATUS  current -- was mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 34 }

       bladeSensor21Volt OBJECT-TYPE
                   SYNTAX  OCTET STRING
                   MAX-ACCESS  read-only
                   STATUS  current -- was mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 35 }

       bladeSensor22Volt OBJECT-TYPE
                   SYNTAX  OCTET STRING
                   MAX-ACCESS  read-only
                   STATUS  current -- was mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 36 }

       bladeSensor23Volt OBJECT-TYPE
                   SYNTAX  OCTET STRING
                   MAX-ACCESS  read-only
                   STATUS  current -- was mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 37 }

       bladeSensor24Volt OBJECT-TYPE
                   SYNTAX  OCTET STRING
                   MAX-ACCESS  read-only
                   STATUS  current -- was mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 38 }

       bladeSensor25Volt OBJECT-TYPE
                   SYNTAX  OCTET STRING
                   MAX-ACCESS  read-only
                   STATUS  current -- was mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 39 }


       bladeSensor26Volt OBJECT-TYPE
                   SYNTAX  OCTET STRING
                   MAX-ACCESS  read-only
                   STATUS  current -- was mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 40 }

       bladeSensor27Volt OBJECT-TYPE
                   SYNTAX  OCTET STRING
                   MAX-ACCESS  read-only
                   STATUS  current -- was mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 41 }
      
      
       bladeSensor28Volt OBJECT-TYPE
                   SYNTAX  OCTET STRING
                   MAX-ACCESS  read-only
                   STATUS  current -- was mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 42 }
      
       bladeSensor29Volt OBJECT-TYPE
                   SYNTAX  OCTET STRING
                   MAX-ACCESS  read-only
                   STATUS  current -- was mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 43 }
      
       bladeSensor30Volt OBJECT-TYPE
                   SYNTAX  OCTET STRING
                   MAX-ACCESS  read-only
                   STATUS  current -- was mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 44 }
      
      
      bladeVoltageThresholdsTable OBJECT-TYPE
                     SYNTAX  SEQUENCE OF BladeVoltageThresholdsEntry
                     MAX-ACCESS  not-accessible
                     STATUS  current -- was mandatory
                     DESCRIPTION
                     "Table of blade VoltageThresholds information."
                     ::= { bladeMonitors 6 }


       bladeVoltageThresholdsEntry OBJECT-TYPE
                     SYNTAX BladeVoltageThresholdsEntry
                     MAX-ACCESS  not-accessible
                     STATUS  current -- was mandatory
                     DESCRIPTION
                     "Blade voltage thresholds table entry"
                     INDEX { voltageThresholdIndex }
                     ::= { bladeVoltageThresholdsTable 1 }


       BladeVoltageThresholdsEntry ::= SEQUENCE {
                   voltageThresholdIndex INTEGER,
                   voltageThresholdBladeId INTEGER,
                   voltageThresholdBladeExists INTEGER,
                   voltageThresholdBladePowerState INTEGER,
                   voltageThresholdBladeName OCTET STRING,
                   bladePlus5VoltHighWarning OCTET STRING,
                   bladePlus5VoltLowWarning OCTET STRING,
                   bladePlus3pt3VoltHighWarning OCTET STRING,
                   bladePlus3pt3VoltLowWarning OCTET STRING,
                   bladePlus12VoltHighWarning OCTET STRING,
                   bladePlus12VoltLowWarning OCTET STRING,
                   bladePlus2pt5VoltHighWarning OCTET STRING,
                   bladePlus2pt5VoltLowWarning OCTET STRING,
                   bladePlus1pt5VoltHighWarning OCTET STRING,
                   bladePlus1pt5VoltLowWarning OCTET STRING,
                   bladePlus1pt25VoltHighWarning OCTET STRING,
                   bladePlus1pt25VoltLowWarning OCTET STRING,
                   bladeVoltThresholdSensorCapability INTEGER,
                   bladeSensor1VoltHighWarning OCTET STRING,
                   bladeSensor1VoltLowWarning OCTET STRING,
                   bladeSensor2VoltHighWarning OCTET STRING,
                   bladeSensor2VoltLowWarning OCTET STRING,
                   bladeSensor3VoltHighWarning OCTET STRING,
                   bladeSensor3VoltLowWarning OCTET STRING,
                   bladeSensor4VoltHighWarning OCTET STRING,
                   bladeSensor4VoltLowWarning OCTET STRING,
                   bladeSensor5VoltHighWarning OCTET STRING,
                   bladeSensor5VoltLowWarning OCTET STRING,
                   bladeSensor6VoltHighWarning OCTET STRING,
                   bladeSensor6VoltLowWarning OCTET STRING,
                   bladeSensor7VoltHighWarning OCTET STRING,
                   bladeSensor7VoltLowWarning OCTET STRING,
                   bladeSensor8VoltHighWarning OCTET STRING,
                   bladeSensor8VoltLowWarning OCTET STRING,
                   bladeSensor9VoltHighWarning OCTET STRING,
                   bladeSensor9VoltLowWarning OCTET STRING,
                   bladeSensor10VoltHighWarning OCTET STRING,
                   bladeSensor10VoltLowWarning OCTET STRING,
                   bladeSensor11VoltHighWarning OCTET STRING,
                   bladeSensor11VoltLowWarning OCTET STRING,
                   bladeSensor12VoltHighWarning OCTET STRING,
                   bladeSensor12VoltLowWarning OCTET STRING,
                   bladeSensor13VoltHighWarning OCTET STRING,
                   bladeSensor13VoltLowWarning OCTET STRING,
                   bladeSensor14VoltHighWarning OCTET STRING,
                   bladeSensor14VoltLowWarning OCTET STRING,
                   bladeSensor15VoltHighWarning OCTET STRING,
                   bladeSensor15VoltLowWarning OCTET STRING,
                   bladeSensor16VoltHighWarning OCTET STRING,
                   bladeSensor16VoltLowWarning OCTET STRING,
                   bladeSensor17VoltHighWarning OCTET STRING,
                   bladeSensor17VoltLowWarning OCTET STRING,
                   bladeSensor18VoltHighWarning OCTET STRING,
                   bladeSensor18VoltLowWarning OCTET STRING,
                   bladeSensor19VoltHighWarning OCTET STRING,
                   bladeSensor19VoltLowWarning OCTET STRING,
                   bladeSensor20VoltHighWarning OCTET STRING,
                   bladeSensor20VoltLowWarning OCTET STRING,
                   bladeSensor21VoltHighWarning OCTET STRING,
                   bladeSensor21VoltLowWarning OCTET STRING,
                   bladeSensor22VoltHighWarning OCTET STRING,
                   bladeSensor22VoltLowWarning OCTET STRING,
                   bladeSensor23VoltHighWarning OCTET STRING,
                   bladeSensor23VoltLowWarning OCTET STRING,
                   bladeSensor24VoltHighWarning OCTET STRING,
                   bladeSensor24VoltLowWarning OCTET STRING,
                   bladeSensor25VoltHighWarning OCTET STRING,
                   bladeSensor25VoltLowWarning OCTET STRING,
                   bladeSensor26VoltHighWarning OCTET STRING,
                   bladeSensor26VoltLowWarning OCTET STRING,
                   bladeSensor27VoltHighWarning OCTET STRING,
                   bladeSensor27VoltLowWarning OCTET STRING,
                   bladeSensor28VoltHighWarning OCTET STRING,
                   bladeSensor28VoltLowWarning OCTET STRING,
                   bladeSensor29VoltHighWarning OCTET STRING,
                   bladeSensor29VoltLowWarning OCTET STRING,
                   bladeSensor30VoltHighWarning OCTET STRING,
                   bladeSensor30VoltLowWarning OCTET STRING
                   }

       voltageThresholdIndex  OBJECT-TYPE
                   SYNTAX  Integer32 (0..2147483647) -- was INTEGER
                   MAX-ACCESS  read-only
                   STATUS  current -- was mandatory
                   DESCRIPTION
                   "Blade voltage thresholds table index."
                   ::= { bladeVoltageThresholdsEntry 1 }


       voltageThresholdBladeId  OBJECT-TYPE
                   SYNTAX  INTEGER {
                     blade1(1),
                     blade2(2),
                     blade3(3),
                     blade4(4),
                     blade5(5),
                     blade6(6),
                     blade7(7),
                     blade8(8),
                     blade9(9),
                     blade10(10),
                     blade11(11),
                     blade12(12),
                     blade13(13),
                     blade14(14)
                   }
                   MAX-ACCESS  read-only
                   STATUS  current -- was mandatory
                   DESCRIPTION
                   "The numeric blade ID."
                   ::= { bladeVoltageThresholdsEntry 2 }

       voltageThresholdBladeExists OBJECT-TYPE
                   SYNTAX  INTEGER {
                     false(0),
                     true(1)
                   }
                   MAX-ACCESS  read-only
                   STATUS  current -- was mandatory
                   DESCRIPTION
                   "Indicates whether the server blade specified exists or not."
                   ::= { bladeVoltageThresholdsEntry 3 }

       voltageThresholdBladePowerState OBJECT-TYPE
                   SYNTAX  INTEGER {
                     off(0),
                     on(1),
                     standby(3),
                     hibernate(4)                     
                   }
                   MAX-ACCESS  read-only
                   STATUS  current -- was mandatory
                   DESCRIPTION
                   "Indicates the power state of the blade specified."
                   ::= { bladeVoltageThresholdsEntry 4 }

       voltageThresholdBladeName OBJECT-TYPE
                   SYNTAX  OCTET STRING
                   MAX-ACCESS  read-write
                   STATUS  current -- was mandatory
                   DESCRIPTION
                   "The name of the blade as a null terminated string."
                   ::= { bladeVoltageThresholdsEntry 5 }

       bladePlus5VoltHighWarning OBJECT-TYPE
                   SYNTAX  OCTET STRING
                   MAX-ACCESS  read-only
                   STATUS  current -- was mandatory
                   DESCRIPTION
                   "Voltage warning threshold reading expressed in Volts(V).
                   If the voltage rises above this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 6 }

       bladePlus5VoltLowWarning OBJECT-TYPE
                   SYNTAX  OCTET STRING
                   MAX-ACCESS  read-only
                   STATUS  current -- was mandatory
                   DESCRIPTION
                   "Voltage warning threshold reading expressed in Volts(V).
                   If the voltage drops below this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 7 }

       bladePlus3pt3VoltHighWarning OBJECT-TYPE
                   SYNTAX  OCTET STRING
                   MAX-ACCESS  read-only
                   STATUS  current -- was mandatory
                   DESCRIPTION
                   "Voltage warning threshold reading expressed in Volts(V).
                   If the voltage rises above this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 8 }

       bladePlus3pt3VoltLowWarning OBJECT-TYPE
                   SYNTAX  OCTET STRING
                   MAX-ACCESS  read-only
                   STATUS  current -- was mandatory
                   DESCRIPTION
                   "Voltage warning threshold reading expressed in Volts(V).
                   If the voltage drops below this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 9 }

       bladePlus12VoltHighWarning OBJECT-TYPE
                   SYNTAX  OCTET STRING
                   MAX-ACCESS  read-only
                   STATUS  current -- was mandatory
                   DESCRIPTION
                   "Voltage warning threshold reading expressed in Volts(V).
                   If the voltage rises above this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 10 }

       bladePlus12VoltLowWarning OBJECT-TYPE
                   SYNTAX  OCTET STRING
                   MAX-ACCESS  read-only
                   STATUS  current -- was mandatory
                   DESCRIPTION
                   "Voltage warning threshold reading expressed in Volts(V).
                   If the voltage drops below this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 11 }

       bladePlus2pt5VoltHighWarning OBJECT-TYPE
                   SYNTAX  OCTET STRING
                   MAX-ACCESS  read-only
                   STATUS  current -- was mandatory
                   DESCRIPTION
                   "Voltage warning threshold reading expressed in Volts(V).
                   If the voltage rises above this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 14 }

       bladePlus2pt5VoltLowWarning OBJECT-TYPE
                   SYNTAX  OCTET STRING
                   MAX-ACCESS  read-only
                   STATUS  current -- was mandatory
                   DESCRIPTION
                   "Voltage warning threshold reading expressed in Volts(V).
                   If the voltage drops below this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 15 }

       bladePlus1pt5VoltHighWarning OBJECT-TYPE
                   SYNTAX  OCTET STRING
                   MAX-ACCESS  read-only
                   STATUS  current -- was mandatory
                   DESCRIPTION
                   "Voltage warning threshold reading expressed in Volts(V).
                   If the voltage rises above this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 16 }

       bladePlus1pt5VoltLowWarning OBJECT-TYPE
                   SYNTAX  OCTET STRING
                   MAX-ACCESS  read-only
                   STATUS  current -- was mandatory
                   DESCRIPTION
                   "Voltage warning threshold reading expressed in Volts(V).
                   If the voltage drops below this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 17 }

       bladePlus1pt25VoltHighWarning OBJECT-TYPE
                   SYNTAX  OCTET STRING
                   MAX-ACCESS  read-only
                   STATUS  current -- was mandatory
                   DESCRIPTION
                   "Voltage warning threshold reading expressed in Volts(V).
                   If the voltage rises above this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 18 }

       bladePlus1pt25VoltLowWarning OBJECT-TYPE
                   SYNTAX  OCTET STRING
                   MAX-ACCESS  read-only
                   STATUS  current -- was mandatory
                   DESCRIPTION
                   "Voltage warning threshold reading expressed in Volts(V).
                   If the voltage drops below this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 19 }

       bladeVoltThresholdSensorCapability OBJECT-TYPE
                   SYNTAX  INTEGER {
                     false(0),
                     true(1)
                   }
                   MAX-ACCESS  read-only
                   STATUS  current -- was mandatory
                   DESCRIPTION
                   "Indicates whether the server blade is IPMI capable or not."
                   ::= { bladeVoltageThresholdsEntry 22 }

       bladeSensor1VoltHighWarning OBJECT-TYPE
                   SYNTAX  OCTET STRING
                   MAX-ACCESS  read-only
                   STATUS  current -- was mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 23 }

       bladeSensor1VoltLowWarning OBJECT-TYPE
                   SYNTAX  OCTET STRING
                   MAX-ACCESS  read-only
                   STATUS  current -- was mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 24 }

       bladeSensor2VoltHighWarning OBJECT-TYPE
                   SYNTAX  OCTET STRING
                   MAX-ACCESS  read-only
                   STATUS  current -- was mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 25 }

       bladeSensor2VoltLowWarning OBJECT-TYPE
                   SYNTAX  OCTET STRING
                   MAX-ACCESS  read-only
                   STATUS  current -- was mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 26 }

       bladeSensor3VoltHighWarning OBJECT-TYPE
                   SYNTAX  OCTET STRING
                   MAX-ACCESS  read-only
                   STATUS  current -- was mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 27 }

       bladeSensor3VoltLowWarning OBJECT-TYPE
                   SYNTAX  OCTET STRING
                   MAX-ACCESS  read-only
                   STATUS  current -- was mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 28 }

       bladeSensor4VoltHighWarning OBJECT-TYPE
                   SYNTAX  OCTET STRING
                   MAX-ACCESS  read-only
                   STATUS  current -- was mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 29 }

       bladeSensor4VoltLowWarning OBJECT-TYPE
                   SYNTAX  OCTET STRING
                   MAX-ACCESS  read-only
                   STATUS  current -- was mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 30 }

       bladeSensor5VoltHighWarning OBJECT-TYPE
                   SYNTAX  OCTET STRING
                   MAX-ACCESS  read-only
                   STATUS  current -- was mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 31 }

       bladeSensor5VoltLowWarning OBJECT-TYPE
                   SYNTAX  OCTET STRING
                   MAX-ACCESS  read-only
                   STATUS  current -- was mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 32 }

       bladeSensor6VoltHighWarning OBJECT-TYPE
                   SYNTAX  OCTET STRING
                   MAX-ACCESS  read-only
                   STATUS  current -- was mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 33 }

       bladeSensor6VoltLowWarning OBJECT-TYPE
                   SYNTAX  OCTET STRING
                   MAX-ACCESS  read-only
                   STATUS  current -- was mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 34 }

       bladeSensor7VoltHighWarning OBJECT-TYPE
                   SYNTAX  OCTET STRING
                   MAX-ACCESS  read-only
                   STATUS  current -- was mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 35 }

       bladeSensor7VoltLowWarning OBJECT-TYPE
                   SYNTAX  OCTET STRING
                   MAX-ACCESS  read-only
                   STATUS  current -- was mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 36 }

       bladeSensor8VoltHighWarning OBJECT-TYPE
                   SYNTAX  OCTET STRING
                   MAX-ACCESS  read-only
                   STATUS  current -- was mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 37 }

       bladeSensor8VoltLowWarning OBJECT-TYPE
                   SYNTAX  OCTET STRING
                   MAX-ACCESS  read-only
                   STATUS  current -- was mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 38 }

       bladeSensor9VoltHighWarning OBJECT-TYPE
                   SYNTAX  OCTET STRING
                   MAX-ACCESS  read-only
                   STATUS  current -- was mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 39 }

       bladeSensor9VoltLowWarning OBJECT-TYPE
                   SYNTAX  OCTET STRING
                   MAX-ACCESS  read-only
                   STATUS  current -- was mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 40 }

       bladeSensor10VoltHighWarning OBJECT-TYPE
                   SYNTAX  OCTET STRING
                   MAX-ACCESS  read-only
                   STATUS  current -- was mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 41 }

       bladeSensor10VoltLowWarning OBJECT-TYPE
                   SYNTAX  OCTET STRING
                   MAX-ACCESS  read-only
                   STATUS  current -- was mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 42 }

       bladeSensor11VoltHighWarning OBJECT-TYPE
                   SYNTAX  OCTET STRING
                   MAX-ACCESS  read-only
                   STATUS  current -- was mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 43 }

       bladeSensor11VoltLowWarning OBJECT-TYPE
                   SYNTAX  OCTET STRING
                   MAX-ACCESS  read-only
                   STATUS  current -- was mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 44 }

       bladeSensor12VoltHighWarning OBJECT-TYPE
                   SYNTAX  OCTET STRING
                   MAX-ACCESS  read-only
                   STATUS  current -- was mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 45 }

       bladeSensor12VoltLowWarning OBJECT-TYPE
                   SYNTAX  OCTET STRING
                   MAX-ACCESS  read-only
                   STATUS  current -- was mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 46 }

       bladeSensor13VoltHighWarning OBJECT-TYPE
                   SYNTAX  OCTET STRING
                   MAX-ACCESS  read-only
                   STATUS  current -- was mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 47 }

       bladeSensor13VoltLowWarning OBJECT-TYPE
                   SYNTAX  OCTET STRING
                   MAX-ACCESS  read-only
                   STATUS  current -- was mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 48 }

       bladeSensor14VoltHighWarning OBJECT-TYPE
                   SYNTAX  OCTET STRING
                   MAX-ACCESS  read-only
                   STATUS  current -- was mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 49 }

       bladeSensor14VoltLowWarning OBJECT-TYPE
                   SYNTAX  OCTET STRING
                   MAX-ACCESS  read-only
                   STATUS  current -- was mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 50 }

       bladeSensor15VoltHighWarning OBJECT-TYPE
                   SYNTAX  OCTET STRING
                   MAX-ACCESS  read-only
                   STATUS  current -- was mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 51 }

       bladeSensor15VoltLowWarning OBJECT-TYPE
                   SYNTAX  OCTET STRING
                   MAX-ACCESS  read-only
                   STATUS  current -- was mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 52 }

       bladeSensor16VoltHighWarning OBJECT-TYPE
                   SYNTAX  OCTET STRING
                   MAX-ACCESS  read-only
                   STATUS  current -- was mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 53 }

       bladeSensor16VoltLowWarning OBJECT-TYPE
                   SYNTAX  OCTET STRING
                   MAX-ACCESS  read-only
                   STATUS  current -- was mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 54 }

       bladeSensor17VoltHighWarning OBJECT-TYPE
                   SYNTAX  OCTET STRING
                   MAX-ACCESS  read-only
                   STATUS  current -- was mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 55 }

       bladeSensor17VoltLowWarning OBJECT-TYPE
                   SYNTAX  OCTET STRING
                   MAX-ACCESS  read-only
                   STATUS  current -- was mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 56 }

       bladeSensor18VoltHighWarning OBJECT-TYPE
                   SYNTAX  OCTET STRING
                   MAX-ACCESS  read-only
                   STATUS  current -- was mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 57 }

       bladeSensor18VoltLowWarning OBJECT-TYPE
                   SYNTAX  OCTET STRING
                   MAX-ACCESS  read-only
                   STATUS  current -- was mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 58 }

       bladeSensor19VoltHighWarning OBJECT-TYPE
                   SYNTAX  OCTET STRING
                   MAX-ACCESS  read-only
                   STATUS  current -- was mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 59 }

       bladeSensor19VoltLowWarning OBJECT-TYPE
                   SYNTAX  OCTET STRING
                   MAX-ACCESS  read-only
                   STATUS  current -- was mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 60 }

       bladeSensor20VoltHighWarning OBJECT-TYPE
                   SYNTAX  OCTET STRING
                   MAX-ACCESS  read-only
                   STATUS  current -- was mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 61 }

       bladeSensor20VoltLowWarning OBJECT-TYPE
                   SYNTAX  OCTET STRING
                   MAX-ACCESS  read-only
                   STATUS  current -- was mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 62 }

       bladeSensor21VoltHighWarning OBJECT-TYPE
                   SYNTAX  OCTET STRING
                   MAX-ACCESS  read-only
                   STATUS  current -- was mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 63 }

       bladeSensor21VoltLowWarning OBJECT-TYPE
                   SYNTAX  OCTET STRING
                   MAX-ACCESS  read-only
                   STATUS  current -- was mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 64 }
                   
       bladeSensor22VoltHighWarning OBJECT-TYPE
                   SYNTAX  OCTET STRING
                   MAX-ACCESS  read-only
                   STATUS  current -- was mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 65 }

       bladeSensor22VoltLowWarning OBJECT-TYPE
                   SYNTAX  OCTET STRING
                   MAX-ACCESS  read-only
                   STATUS  current -- was mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 66 }

       bladeSensor23VoltHighWarning OBJECT-TYPE
                   SYNTAX  OCTET STRING
                   MAX-ACCESS  read-only
                   STATUS  current -- was mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 67 }

       bladeSensor23VoltLowWarning OBJECT-TYPE
                   SYNTAX  OCTET STRING
                   MAX-ACCESS  read-only
                   STATUS  current -- was mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 68 }

       bladeSensor24VoltHighWarning OBJECT-TYPE
                   SYNTAX  OCTET STRING
                   MAX-ACCESS  read-only
                   STATUS  current -- was mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 69 }

       bladeSensor24VoltLowWarning OBJECT-TYPE
                   SYNTAX  OCTET STRING
                   MAX-ACCESS  read-only
                   STATUS  current -- was mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 70 }

       bladeSensor25VoltHighWarning OBJECT-TYPE
                   SYNTAX  OCTET STRING
                   MAX-ACCESS  read-only
                   STATUS  current -- was mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 71 }

       bladeSensor25VoltLowWarning OBJECT-TYPE
                   SYNTAX  OCTET STRING
                   MAX-ACCESS  read-only
                   STATUS  current -- was mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 72 }


       bladeSensor26VoltHighWarning OBJECT-TYPE
                   SYNTAX  OCTET STRING
                   MAX-ACCESS  read-only
                   STATUS  current -- was mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 73 }

       bladeSensor26VoltLowWarning OBJECT-TYPE
                   SYNTAX  OCTET STRING
                   MAX-ACCESS  read-only
                   STATUS  current -- was mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 74 }

       bladeSensor27VoltHighWarning OBJECT-TYPE
                   SYNTAX  OCTET STRING
                   MAX-ACCESS  read-only
                   STATUS  current -- was mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 75 }

       bladeSensor27VoltLowWarning OBJECT-TYPE
                   SYNTAX  OCTET STRING
                   MAX-ACCESS  read-only
                   STATUS  current -- was mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 76 }

       bladeSensor28VoltHighWarning OBJECT-TYPE
                   SYNTAX  OCTET STRING
                   MAX-ACCESS  read-only
                   STATUS  current -- was mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 77 }

       bladeSensor28VoltLowWarning OBJECT-TYPE
                   SYNTAX  OCTET STRING
                   MAX-ACCESS  read-only
                   STATUS  current -- was mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 78 }

       bladeSensor29VoltHighWarning OBJECT-TYPE
                   SYNTAX  OCTET STRING
                   MAX-ACCESS  read-only
                   STATUS  current -- was mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 79 }

       bladeSensor29VoltLowWarning OBJECT-TYPE
                   SYNTAX  OCTET STRING
                   MAX-ACCESS  read-only
                   STATUS  current -- was mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 80 }

       bladeSensor30VoltHighWarning OBJECT-TYPE
                   SYNTAX  OCTET STRING
                   MAX-ACCESS  read-only
                   STATUS  current -- was mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 81 }

       bladeSensor30VoltLowWarning OBJECT-TYPE
                   SYNTAX  OCTET STRING
                   MAX-ACCESS  read-only
                   STATUS  current -- was mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 82 }

      bladePowerRestart OBJECT IDENTIFIER ::= { processorBlade 6 }
       -- blade power/restart control

        bladePowerRestartTable OBJECT-TYPE
                       SYNTAX  SEQUENCE OF BladePowerRestartEntry
                       MAX-ACCESS  not-accessible
                       STATUS  current -- was mandatory
                       DESCRIPTION
                       "Table of blade remote power control information.
                       Contains power on/off enablement status for each blade."
                       ::= { bladePowerRestart 1 }

         bladePowerRestartEntry OBJECT-TYPE
                       SYNTAX BladePowerRestartEntry
                       MAX-ACCESS  not-accessible
                       STATUS  current -- was mandatory
                       DESCRIPTION
                       "Blade power restart table entry"
                       INDEX { powerRestartIndex }
                       ::= { bladePowerRestartTable 1 }


         BladePowerRestartEntry ::= SEQUENCE {
                     powerRestartIndex INTEGER,
                     powerRestartBladeId INTEGER,
                     powerRestartBladeExists INTEGER,
                     powerRestartBladePowerState INTEGER,
                     powerRestartBladeHealthState INTEGER,
                     powerRestartBladeName OCTET STRING,
                     powerOnOffBlade INTEGER,
                     restartBlade INTEGER,
                     restartBladeSMP INTEGER,
                     restartBladeNMI INTEGER,
                     restartBladeClearNVRAM INTEGER,
                     restartBladeInvokeDiags INTEGER,
                     restartBladeInvokeDiagsFromDefaultBootList INTEGER
                     }

         powerRestartIndex  OBJECT-TYPE
                     SYNTAX  Integer32 (0..2147483647) -- was INTEGER
                     MAX-ACCESS  read-only
                     STATUS  current -- was mandatory
                     DESCRIPTION
                     "Blade power restart table index."
                     ::= { bladePowerRestartEntry 1 }


         powerRestartBladeId  OBJECT-TYPE
                     SYNTAX  INTEGER {
                       blade1(1),
                       blade2(2),
                       blade3(3),
                       blade4(4),
                       blade5(5),
                       blade6(6),
                       blade7(7),
                       blade8(8),
                       blade9(9),
                       blade10(10),
                       blade11(11),
                       blade12(12),
                       blade13(13),
                       blade14(14)
                     }
                     MAX-ACCESS  read-only
                     STATUS  current -- was mandatory
                     DESCRIPTION
                     "The numeric blade ID."
                     ::= { bladePowerRestartEntry 2 }

         powerRestartBladeExists OBJECT-TYPE
                     SYNTAX  INTEGER {
                       false(0),
                       true(1)
                     }
                     MAX-ACCESS  read-only
                     STATUS  current -- was mandatory
                     DESCRIPTION
                     "Indicates whether the server blade specified exists or not."
                     ::= { bladePowerRestartEntry 3 }

         powerRestartBladePowerState OBJECT-TYPE
                     SYNTAX  INTEGER {
                       off(0),
                       on(1),
                       standby(3),
                       hibernate(4)                       
                     }
                     MAX-ACCESS  read-only
                     STATUS  current -- was mandatory
                     DESCRIPTION
                     "Indicates the power state of the blade specified."
                     ::= { bladePowerRestartEntry 4 }

         powerRestartBladeHealthState  OBJECT-TYPE
                   SYNTAX  INTEGER {
                     unknown(0),
                     good(1),
                     warning(2),
                     critical(3),
                     kernelMode(4),
                     discovering(5),
                     commError(6),
                     noPower(7),
                     flashing(8),
                     initFailure(9),
                     insufficientPower(10),
                     powerDenied(11)
                   }
                   MAX-ACCESS  read-only
                   STATUS  current -- was mandatory
                   DESCRIPTION
                   "The system health state for the blade.

                    Unknown: Blade is in an undefined state.
                    Good: Blade is operating normally.
                    Warning: One or more outstanding warnings exist for this blade.
                    Critical: One or more outstanding critical events for this blade.
                    Kernel Mode: Blade is in kernel mode.
                    Discovering: The AMM is currently in the process of discovering this blade.
                    Communications Error: The AMM failed to communicate with this blade.
                    No Power: No power to the blade's domain.
                    Flashing: Flashing in progress.
                    Initialization Failure: Blade failed to initialized.
                    Insufficient Power: Not enough power is left in the blade's domain to power the blade.
                    Power Denied: Power was denied to the blade."
                   ::= { bladePowerRestartEntry 5 }

         powerRestartBladeName OBJECT-TYPE
                     SYNTAX  OCTET STRING
                     MAX-ACCESS  read-only
                     STATUS  current -- was mandatory
                     DESCRIPTION
                     "The name of the blade as a null terminated string."
                     ::= { bladePowerRestartEntry 6 }

         powerOnOffBlade OBJECT-TYPE
                     SYNTAX  INTEGER {
                       off(0),
                       on(1),
                       softoff(2)
                     }
                     MAX-ACCESS  read-write
                     STATUS  current -- was mandatory
                     DESCRIPTION
                     "Control the power state of a specific blade.
                     
                     Off: Power Off Blade.
                     On:  Power On Blade.
                     Softoff: Shut Down OS and Power Off Blade. This operation is not
                              supported on all blades.
                     
                     NOTE: Value returned for the GET command is meaningless 
                     for this MIB object. The powerRestartBladePowerState MIB object should be
                     used to check the power state of the blade(s)"
                     ::= { bladePowerRestartEntry 7 }

         restartBlade OBJECT-TYPE
                     SYNTAX  INTEGER {
                       execute(1)
                     }
                     MAX-ACCESS  read-write
                     STATUS  current -- was mandatory
                     DESCRIPTION
                     "Restart a blade.
                     
                     NOTE: Value returned for the GET command is meaningless
                     for this MIB object."
                     ::= { bladePowerRestartEntry 8 }

         restartBladeSMP OBJECT-TYPE
                     SYNTAX  INTEGER {
                       execute(1)
                     }
                     MAX-ACCESS  read-write
                     STATUS  current -- was mandatory
                     DESCRIPTION
                     "Restart a blade's system management processor.
                     
                     NOTE: Value returned for the GET command is meaningless 
                     for this MIB object."
                     ::= { bladePowerRestartEntry 9 }

         restartBladeNMI OBJECT-TYPE
                     SYNTAX  INTEGER {
                       execute(1)
                     }
                     MAX-ACCESS  read-write
                     STATUS  current -- was mandatory
                     DESCRIPTION
                     "Soft reset and initiate a dump on a blade.  This option is not supported
                     on all blades.
                     
                     NOTE: Value returned for the GET command is meaningless 
                     for this MIB object."
                     ::= { bladePowerRestartEntry 10 }
         
         restartBladeClearNVRAM OBJECT-TYPE
                     SYNTAX  INTEGER {
                       execute(1)
                     }
                     MAX-ACCESS  read-write
                     STATUS  current -- was mandatory
                     DESCRIPTION
                     "Restart a blade and set NVRAM to default values.  This option is not 
                     supported on all blades.
                     
                     NOTE: Value returned for the GET command is meaningless 
                     for this MIB object."
                     ::= { bladePowerRestartEntry 11 }

         restartBladeInvokeDiags OBJECT-TYPE
                     SYNTAX  INTEGER {
                       execute(1)
                     }
                     MAX-ACCESS  read-write
                     STATUS  current -- was mandatory
                     DESCRIPTION
                     "Restart a blade and boot into diagnostic mode.  This option is not 
                     supported on all blades.
                     
                     NOTE: Value returned for the GET command is meaningless 
                     for this MIB object."
                     ::= { bladePowerRestartEntry 12 }

         restartBladeInvokeDiagsFromDefaultBootList OBJECT-TYPE
                     SYNTAX  INTEGER {
                       execute(1)
                     }
                     MAX-ACCESS  read-write
                     STATUS  current -- was mandatory
                     DESCRIPTION
                     "Restart a blade and boot into diagnostic mode from Default Boot List
                     as defined on the blade.  This option is not supported on all blades.
                     
                     NOTE: Value returned for the GET command is meaningless 
                     for this MIB object."
                     ::= { bladePowerRestartEntry 13 }


      bladeConfiguration OBJECT IDENTIFIER ::= { processorBlade 7 }
       -- blade power/restart control

        bladeConfigurationTable OBJECT-TYPE
                       SYNTAX  SEQUENCE OF BladeConfigurationEntry
                       MAX-ACCESS  not-accessible
                       STATUS  current -- was mandatory
                       DESCRIPTION
                       "Table of blade remote power control information.
                       Contains power on/off enablement status for each blade."
                       ::= { bladeConfiguration 1 }

         bladeConfigurationEntry OBJECT-TYPE
                       SYNTAX BladeConfigurationEntry
                       MAX-ACCESS  not-accessible
                       STATUS  current -- was mandatory
                       DESCRIPTION
                       "Blade configuration table entry"
                       INDEX { configurationIndex }
                       ::= { bladeConfigurationTable 1 }


         BladeConfigurationEntry ::= SEQUENCE {
                     configurationIndex INTEGER,
                     configurationBladeId INTEGER,
                     configurationBladeExists INTEGER,
                     configurationBladePowerState INTEGER,
                     configurationBladeName OCTET STRING,
                     configurationBladecKVM INTEGER,
                     configurationBladeActiveBootMode INTEGER,
                     configurationBladePendingBootMode INTEGER
                     }

         configurationIndex  OBJECT-TYPE
                     SYNTAX  Integer32 (0..2147483647) -- was INTEGER
                     MAX-ACCESS  read-only
                     STATUS  current -- was mandatory
                     DESCRIPTION
                     "Blade configuration table index."
                     ::= { bladeConfigurationEntry 1 }


         configurationBladeId  OBJECT-TYPE
                     SYNTAX  INTEGER {
                       blade1(1),
                       blade2(2),
                       blade3(3),
                       blade4(4),
                       blade5(5),
                       blade6(6),
                       blade7(7),
                       blade8(8),
                       blade9(9),
                       blade10(10),
                       blade11(11),
                       blade12(12),
                       blade13(13),
                       blade14(14)
                     }
                     MAX-ACCESS  read-only
                     STATUS  current -- was mandatory
                     DESCRIPTION
                     "The numeric blade ID."
                     ::= { bladeConfigurationEntry 2 }

         configurationBladeExists OBJECT-TYPE
                     SYNTAX  INTEGER {
                       false(0),
                       true(1)
                     }
                     MAX-ACCESS  read-only
                     STATUS  current -- was mandatory
                     DESCRIPTION
                     "Indicates whether the server blade specified exists or not."
                     ::= { bladeConfigurationEntry 3 }

         configurationBladePowerState OBJECT-TYPE
                     SYNTAX  INTEGER {
                       off(0),
                       on(1),
                       standby(3),
                       hibernate(4)                       
                     }
                     MAX-ACCESS  read-only
                     STATUS  current -- was mandatory
                     DESCRIPTION
                     "Indicates the power state of the blade specified."
                     ::= { bladeConfigurationEntry 4 }

         configurationBladeName OBJECT-TYPE
                     SYNTAX  OCTET STRING
                     MAX-ACCESS  read-write
                     STATUS  current -- was mandatory
                     DESCRIPTION
                     "The name of the blade as a null terminated string."
                     ::= { bladeConfigurationEntry 5 }

         configurationBladecKVM OBJECT-TYPE
                     SYNTAX  INTEGER {
                       disable(0),
                       enable(1),
                       notPresent(2)
                     }
                     MAX-ACCESS  read-write
                     STATUS  current -- was mandatory
                     DESCRIPTION
                     "Enable or disable the concurrent KVM function on specified blade.
                     If concurrent KVM is not supported by the blade, it displays 'notPresent' 
                     and the concurrent KVM functionality can not be enabled or disabled."
                     ::= { bladeConfigurationEntry 6 }

         configurationBladeActiveBootMode OBJECT-TYPE
                     SYNTAX  INTEGER {
                       temporary(1),
                       permanent(2),
                       notApplicable(255)
                     }
                     MAX-ACCESS  read-only
                     STATUS  current -- was mandatory
                     DESCRIPTION
                     "Indicates the active copy of the firmware from which the blade is booting.
                     NOTE: Some blades do not support the automatic boot recovery. It displays
                     'notApplicable' for such blades.
                     Booting from the temporary copy is recommended since it typically contains the
                     latest enhancements and fixes. Switching to the permanent copy should be reserved
                     for when booting from the temporary copy is no longer possible."
                     ::= { bladeConfigurationEntry 7 }

         configurationBladePendingBootMode OBJECT-TYPE
                     SYNTAX  INTEGER {
                       temporary(1),
                       permanent(2),
                       notApplicable(255)
                     }
                     MAX-ACCESS  read-write
                     STATUS  current -- was mandatory
                     DESCRIPTION
                     "Indicates the copy of the firmware from which the blade will boot 
                     after the next reboot.
                     NOTE: Some blades do not support the automatic boot recovery. It displays
                     'notApplicable' for such blades and the value can not be set.
                     Booting from the temporary copy is recommended since it typically contains the
                     latest enhancements and fixes. Switching to the permanent copy should be reserved
                     for when booting from the temporary copy is no longer possible."
                     ::= { bladeConfigurationEntry 8 }

        -- Power Management Policy Settings
        bladePowerManagementPolicy OBJECT IDENTIFIER ::= { bladeConfiguration 2 }

          powerdomain1Oversubscription OBJECT-TYPE
                     SYNTAX  INTEGER {
                       not-allowed(0),
                       recoverable(1),
                       non-recoverable(2)
                     }
                     MAX-ACCESS  read-write
                     STATUS  current -- was mandatory
                     DESCRIPTION
                     "Power Management Policy settings for power domain 1."
                     ::= { bladePowerManagementPolicy 1 }

          powerdomain2Oversubscription OBJECT-TYPE
                     SYNTAX  INTEGER {
                       not-allowed(0),
                       recoverable(1),
                       non-recoverable(2)
                     }
                     MAX-ACCESS  read-write
                     STATUS  current -- was mandatory
                     DESCRIPTION
                     "Power Management Policy settings for power domain 2."
                     ::= { bladePowerManagementPolicy 2 }

          acousticMode OBJECT-TYPE
                     SYNTAX  INTEGER {
                       disabled(0),
                       enabled(1)
                     }
                     MAX-ACCESS  read-write
                     STATUS  current -- was mandatory
                     DESCRIPTION
                     "Acoustic mode setting for thermal conditions"
                     ::= { bladePowerManagementPolicy 3 }

          nebsMode OBJECT-TYPE
                     SYNTAX  INTEGER {
                       disabled(0),
                       enabled(1)
                     }
                     MAX-ACCESS  read-write
                     STATUS  current -- was mandatory
                     DESCRIPTION
                     "NEBS (Network Equipment-Building System) mode setting for thermal conditions. 
                      NOTE: This MIB object is for BladeCenter T, HT and TR only."
                     ::= { bladePowerManagementPolicy 4 }          

        bladecKVMEnableDisable OBJECT-TYPE
                      SYNTAX  INTEGER  {
                        disable(0),
                        enable(1)
                      }  
                      MAX-ACCESS  read-write
                      STATUS  current -- was mandatory
                      DESCRIPTION
                      "Enable or disable cKVM function on all server blades."  
                      ::= { bladeConfiguration 3 }

      bladeIPAddrRangeStart OBJECT-TYPE
                      SYNTAX  IpAddress
                      MAX-ACCESS  read-write
                      STATUS  current -- was mandatory
                      DESCRIPTION
                      "This field is used to configure the start of the IP address range for the blade 
                      system management processors on the blades.  These addresses are used on the 
                      internal management network between the MM and the blade BSMPs.  For example the 
                      value of 10.10.10.1 means the BSMP on the blade in bay 1 will have IP address 
                      10.10.10.1, the BSMP on the blade in bay 2 will have IP address 10.10.10.2 and so on."  
                      ::= { processorBlade 8 }
                      

      bladeCapacityOnDemand OBJECT IDENTIFIER ::= { processorBlade 9 }

        bladeCapacityOnDemandTable OBJECT-TYPE
                       SYNTAX  SEQUENCE OF BladeCapacityOnDemandEntry
                       MAX-ACCESS  not-accessible
                       STATUS  deprecated
                       DESCRIPTION
                       "Table of COD blade.

                       NOTE: This table is deprecated and no longer supported." 
                       ::= { bladeCapacityOnDemand 1 }

         bladeCapacityOnDemandEntry OBJECT-TYPE
                       SYNTAX BladeCapacityOnDemandEntry
                       MAX-ACCESS  not-accessible
                       STATUS  deprecated
                       DESCRIPTION
                       "Blade COD table entry
                       NOTE: This table is deprecated and no longer supported." 
                       INDEX { bladeCapacityOnDemandIndex }
                       ::= { bladeCapacityOnDemandTable 1 }

         BladeCapacityOnDemandEntry ::= SEQUENCE {
                     bladeCapacityOnDemandIndex INTEGER,             -- deprecated
                     bladeCapacityOnDemandBladeName OCTET STRING,    -- deprecated
                     bladeCapacityOnDemandState INTEGER              -- deprecated
                     }

         bladeCapacityOnDemandIndex  OBJECT-TYPE
                     SYNTAX  Integer32 (0..2147483647) -- was INTEGER
                     MAX-ACCESS  read-only
                     STATUS  deprecated
                     DESCRIPTION
                     "Blade configuration table index.
                      NOTE: This Mib object is deprecated and no longer supported." 
                     ::= { bladeCapacityOnDemandEntry 1 }

         bladeCapacityOnDemandBladeName OBJECT-TYPE
                     SYNTAX  OCTET STRING
                     MAX-ACCESS  read-only
                     STATUS  deprecated
                     DESCRIPTION
                     "The name of the blade as a null terminated string.
                      NOTE: This Mib object is deprecated and no longer supported." 
                     ::= { bladeCapacityOnDemandEntry 2 }

         bladeCapacityOnDemandState  OBJECT-TYPE
                     SYNTAX  INTEGER {
                       none(0),
                       standby(1),
                       active(2)
                     }
                     MAX-ACCESS  read-write
                     STATUS  deprecated
                     DESCRIPTION
                     "The state of Capacity On Demand.
                      NOTE: This Mib object is deprecated and no longer supported." 
                     ::= { bladeCapacityOnDemandEntry 3 }


-- CIRPAK_MODS
       
      bladeBootCountPowerOnTime OBJECT IDENTIFIER ::= { processorBlade 10 }
       -- blade Count of number of boots for a blade and its Power On Time

        bladeBootCountPowerOnTimeTable OBJECT-TYPE
                       SYNTAX  SEQUENCE OF BladeBootCountPowerOnTimeEntry
                       MAX-ACCESS  not-accessible
                       STATUS  current -- was mandatory
                       DESCRIPTION
                       "Table per blade of the number of boots for the blade and 
                       the number of seconds the blade has been powered on."
                       ::= { bladeBootCountPowerOnTime 1 }

         bladeBootCountPowerOnTimeEntry OBJECT-TYPE
                       SYNTAX BladeBootCountPowerOnTimeEntry
                       MAX-ACCESS  not-accessible
                       STATUS  current -- was mandatory
                       DESCRIPTION
                       "The number of boots for the blade and 
                       the number of seconds the blade has been powered on."
                       INDEX { bootCountPowerOnTimeBladeIndex }
                       ::= { bladeBootCountPowerOnTimeTable 1 }


         BladeBootCountPowerOnTimeEntry ::= SEQUENCE {
                   bootCountPowerOnTimeBladeIndex INTEGER,
                   bootCountPowerOnTimeBladeId    INTEGER,
                   bootCountPowerOnTimeBoots      INTEGER,
                   bootCountPowerOnTimeSecs       INTEGER
                   }
         
         bootCountPowerOnTimeBladeIndex  OBJECT-TYPE
                     SYNTAX  Integer32 (0..2147483647) -- was INTEGER
                     MAX-ACCESS  read-only
                     STATUS  current -- was mandatory
                     DESCRIPTION
                     "Blade boot count/Power On Time table index."
                     ::= { bladeBootCountPowerOnTimeEntry 1 }
                     
         bootCountPowerOnTimeBladeId  OBJECT-TYPE
                     SYNTAX  INTEGER {
                       blade1(1),
                       blade2(2),
                       blade3(3),
                       blade4(4),
                       blade5(5),
                       blade6(6),
                       blade7(7),
                       blade8(8),
                       blade9(9),
                       blade10(10),
                       blade11(11),
                       blade12(12),
                       blade13(13),
                       blade14(14)
                     }
                     MAX-ACCESS  read-only
                     STATUS  current -- was mandatory
                     DESCRIPTION
                     "The numeric blade ID."
                     ::= { bladeBootCountPowerOnTimeEntry 2 }
                     
         bootCountPowerOnTimeBoots  OBJECT-TYPE
                     SYNTAX  INTEGER
                     MAX-ACCESS  read-write
                     STATUS  current -- was mandatory
                     DESCRIPTION
                     "Blade Boot Count. If there is no blade in the
                     given slot then this value is undefined. Writing this
                     value resets the Boot Count to zero."
                     ::= { bladeBootCountPowerOnTimeEntry 3 }
                     
         bootCountPowerOnTimeSecs  OBJECT-TYPE
                     SYNTAX  INTEGER
                     MAX-ACCESS  read-write
                     STATUS  current -- was mandatory
                     DESCRIPTION
                     "Blade Power On Time in seconds. If there is no blade in
                     the given slot then this value is undefined. Writing this
                     value resets the Power On Time to zero."
                     ::= { bladeBootCountPowerOnTimeEntry 4 }

      bladeVlanId OBJECT-TYPE
                  SYNTAX  INTEGER
                  MAX-ACCESS  read-write
                  STATUS  current -- was mandatory
                  DESCRIPTION
                  "This is the virtual LAN ID for the internal management network between the MM and 
                  the blade system management processors (BSMPs).  The range of valid VLAN ID's 
                  is 1 to 4095."
                  ::= { processorBlade 11 }


---
--- Blade Bay Data Table MIB objects
---
        bladeBayDataTable OBJECT-TYPE
                SYNTAX SEQUENCE OF BladeBayDataEntry
                MAX-ACCESS not-accessible
                STATUS current -- was mandatory
                DESCRIPTION
                        "Table of blade bay data (BBD) information."
                ::= { processorBlade 13 }

        bladeBayDataEntry OBJECT-TYPE
                SYNTAX BladeBayDataEntry
                MAX-ACCESS not-accessible
                STATUS current -- was mandatory
                DESCRIPTION
                        "Blade bay data (BBD) table entry."
                INDEX { bayDataIndex }
                ::= { bladeBayDataTable 1 }

        BladeBayDataEntry ::= SEQUENCE {
                bayDataIndex INTEGER,
                bayDataBladeId INTEGER,
                bayDataBladeExists INTEGER,
                bayDataBladePowerState INTEGER,
                bayDataBladeName OCTET STRING,
                bayData OCTET STRING,
                bayDataBladeStatus INTEGER
                }

        bayDataIndex OBJECT-TYPE
                SYNTAX Integer32 (0..2147483647) -- was INTEGER
                MAX-ACCESS read-only
                STATUS current -- was mandatory
                DESCRIPTION
                        "Blade bay data (BBD) table index."
                ::= { bladeBayDataEntry 1 }
                
        bayDataBladeId OBJECT-TYPE
                SYNTAX INTEGER {
                        blade1(1),
                        blade2(2),
                        blade3(3),
                        blade4(4),
                        blade5(5),
                        blade6(6),
                        blade7(7),
                        blade8(8),
                        blade9(9),
                        blade10(10),
                        blade11(11),
                        blade12(12),
                        blade13(13),
                        blade14(14)
                }
                MAX-ACCESS read-only
                STATUS current -- was mandatory
                DESCRIPTION
                        "The numeric blade ID."
                ::= { bladeBayDataEntry 2 }

        bayDataBladeExists OBJECT-TYPE
                SYNTAX INTEGER {
                        false(0),
                        true(1)
                }
                MAX-ACCESS read-only
                STATUS current -- was mandatory
                DESCRIPTION
                        "Indicates whether the server blade specified exists or not."
                ::= { bladeBayDataEntry 3 }

        bayDataBladePowerState OBJECT-TYPE
                SYNTAX INTEGER {
                        off(0),
                        on(1),
                        standby(3),
                        hibernate(4)
                }
                MAX-ACCESS read-only
                STATUS current -- was mandatory
                DESCRIPTION
                        "Indicates the power state of the blade specified."
                ::= { bladeBayDataEntry 4 }
        
        bayDataBladeName OBJECT-TYPE
                SYNTAX OCTET STRING
                MAX-ACCESS read-only
                STATUS current -- was mandatory
                DESCRIPTION
                        "The name of the blade as a null terminated string."
                ::= { bladeBayDataEntry 5 }


        bayData OBJECT-TYPE
                SYNTAX OCTET STRING
                MAX-ACCESS read-write
                STATUS current -- was mandatory
                DESCRIPTION
                        "A null terminated string that defines the Blade Bay Data (BBD). This data
                        is pushed to the blade's BSMP and SMBIOS structures, where it can used
                        by the blade's OS. Up to 60 characters can be defined plus a Null
                        terminator."
                ::= { bladeBayDataEntry 6 }

        bayDataBladeStatus OBJECT-TYPE
                SYNTAX INTEGER {
                        supported(0),
                        bsmp(1),
                        notPresent(2),
                        discovering(3),
                        notApplicable(255)
                }
                MAX-ACCESS read-only
                STATUS current -- was mandatory
                DESCRIPTION
                        "This shows Blade Bay Data (BBD) status. 0 means the blade fully 
                        supports BBD; 1 means that the blade's BIOS does not support BBD; 
                        2 means that there is no blade in the bay; 3 means that the blade is
                        being discovered. 255 means that the blade does not support BBD."
                ::= { bladeBayDataEntry 7 }


      bladeNetworkConfiguration  OBJECT IDENTIFIER ::= { processorBlade 12 }
      -- blade network configuration for all blades

        bladeNetworkInterfaceTable OBJECT-TYPE
                       SYNTAX  SEQUENCE OF BladeNetworkInterfaceEntry
                       MAX-ACCESS  not-accessible
                       STATUS  current -- was mandatory
                       DESCRIPTION
                       "Table of all blades' network interfaces."
                       ::= { bladeNetworkConfiguration 2 }

         bladeNetworkInterfaceEntry OBJECT-TYPE
                       SYNTAX  BladeNetworkInterfaceEntry
                       MAX-ACCESS  not-accessible
                       STATUS  current -- was mandatory
                       DESCRIPTION
                       "Blade configuration table entry"
                       INDEX { bladeNetworkInterfaceIndex }
                       ::= { bladeNetworkInterfaceTable 1 }

         BladeNetworkInterfaceEntry ::= SEQUENCE {
                     bladeNetworkInterfaceIndex INTEGER,
                     bladeNetworkInterfaceBayNumber OCTET STRING,
                     bladeNetworkInterfaceNumber INTEGER,
                     bladeNetworkInterfaceType INTEGER,
                     bladeNetworkInterfaceLabel OCTET STRING,
                     bladeNetworkInterfaceIPAddr IpAddress,
                     bladeNetworkInterfaceSubnetMask IpAddress,
                     bladeNetworkInterfaceGatewayAddr IpAddress,
                     bladeNetworkInterfaceVlanId INTEGER,
                     bladeNetworkInterfaceVlanEnable INTEGER,
                     bladeNetworkInterfaceEnable INTEGER,
                     bladeNetworkInterfaceDHCPEnable INTEGER,
                     bladeNetworkInterfaceMACAddr OCTET STRING
                     }

         bladeNetworkInterfaceIndex  OBJECT-TYPE
                     SYNTAX  Integer32 (0..2147483647) -- was INTEGER
                     MAX-ACCESS  read-only
                     STATUS  current -- was mandatory
                     DESCRIPTION
                     "Blade Network Interface Table index."
                     ::= { bladeNetworkInterfaceEntry 1 }

         bladeNetworkInterfaceBayNumber OBJECT-TYPE
                     SYNTAX  OCTET STRING
                     MAX-ACCESS  read-only
                     STATUS  current -- was mandatory
                     DESCRIPTION
                     "The bay number of the main server blade that supports network interface management"
                     ::= { bladeNetworkInterfaceEntry 2 }

         bladeNetworkInterfaceNumber OBJECT-TYPE
                     SYNTAX  INTEGER 
                     MAX-ACCESS  read-only
                     STATUS  current -- was mandatory
                     DESCRIPTION
                     "Indicates which network interface on the blade System Management Processor is be read or writen"
                     ::= { bladeNetworkInterfaceEntry 3 }

         bladeNetworkInterfaceType OBJECT-TYPE
                     SYNTAX  INTEGER {
                       public(1),
                       private(2)
                     }
                     MAX-ACCESS  read-only
                     STATUS  current -- was mandatory
                     DESCRIPTION
                     "Indicates blade network interface type."
                     ::= { bladeNetworkInterfaceEntry 4 }

         bladeNetworkInterfaceLabel OBJECT-TYPE
                     SYNTAX  OCTET STRING
                     MAX-ACCESS  read-only
                     STATUS  current -- was mandatory
                     DESCRIPTION
                     "Show string label that identifies the interface."
                     ::= { bladeNetworkInterfaceEntry 5 }

         bladeNetworkInterfaceIPAddr OBJECT-TYPE
                     SYNTAX  IpAddress
                     MAX-ACCESS  read-write
                     STATUS  current -- was mandatory
                     DESCRIPTION
                     "Show/modify current IP address of the blade network interface.
                     Note that only if the bladeNetworkInterfaceEnable is 'enabled(1)' and the bladeNetworkInterfaceDHCPEnable is not 'dhcpEnabled(1)', should the IP address be 
                     pushed down to blade System Management Processor"
                     ::= { bladeNetworkInterfaceEntry 6 }

         bladeNetworkInterfaceSubnetMask OBJECT-TYPE
                     SYNTAX  IpAddress
                     MAX-ACCESS  read-write
                     STATUS  current -- was mandatory
                     DESCRIPTION
                     "Show or modifie current subnet mask of the blade network interface.
                     Note that only if the bladeNetworkInterfaceEnable is 'enabled(1)' and the bladeNetworkInterfaceDHCPEnable is not 'dhcpEnabled(1)', should the SunnetMask be 
                     pushed down to blade System Management Processor"
                     ::= { bladeNetworkInterfaceEntry 7 }

         bladeNetworkInterfaceGatewayAddr OBJECT-TYPE
                     SYNTAX  IpAddress
                     MAX-ACCESS  read-write
                     STATUS  current -- was mandatory
                     DESCRIPTION
                     "Show or modify current IP gateway of the blade network interface.
                     Note that only if the bladeNetworkInterfaceEnable is 'enabled(1)' and the bladeNetworkInterfaceDHCPEnable is not 'dhcpEnabled(1)', should the Gateway address be 
                     pushed down to blade System Management Processor"
                     ::= { bladeNetworkInterfaceEntry 8 }

         bladeNetworkInterfaceVlanId   OBJECT-TYPE
                     SYNTAX  INTEGER
                      MAX-ACCESS  read-write
                      STATUS  current -- was mandatory
                      DESCRIPTION
                      "This is the virtual LAN ID for the network interface cards (NICs). The range of valid VLAN ID's is 0 to 4095.
                      Note that only if the bladeNetworkInterfaceEnable is 'enabled(1)' and the bladeNetworkInterfaceType is 'public(1)', should the VLAN ID be 
                      pushed down to blade System Management Processor"
                      ::= { bladeNetworkInterfaceEntry 9 }

        bladeNetworkInterfaceVlanEnable  OBJECT-TYPE
                     SYNTAX  INTEGER {
                       disabled(0),
                       enabled(1),
                       notApplicable(255)
                      }
                      MAX-ACCESS  read-write
                      STATUS  current -- was mandatory
                      DESCRIPTION
                      "enabled/diabled existing VLAN ID for the ethernet interface configure.
                      Note that only if the bladeNetworkInterfaceEnable is 'enabled(1)' and the bladeNetworkInterfaceType is 'public(1)', should the VLAN Enable be 
                      pushed down to blade System Management Processor"
                      ::= { bladeNetworkInterfaceEntry 10 }

         bladeNetworkInterfaceEnable OBJECT-TYPE
                     SYNTAX  INTEGER {
                       disabled(0),
                       enabled(1),
                       notApplicable(255)
                     }
                     MAX-ACCESS  read-write
                     STATUS  current -- was mandatory
                     DESCRIPTION
                     "Disabled or enabled the blade network interface. If the network interface is disalbed, then ignore other configurations.
                     If this network interface doesn't support enabled/disabled, show 'notApplicable(255)'"
                     ::= { bladeNetworkInterfaceEntry 11 }

         bladeNetworkInterfaceDHCPEnable OBJECT-TYPE
                     SYNTAX  INTEGER {
                        dhcpDisabled(0),
                        dhcpEnabled(1),
                        tryDhcpThenTryStatic(2),
                        notApplicable(255)
                     }
                     MAX-ACCESS  read-write
                     STATUS  current -- was mandatory
                     DESCRIPTION
                     "IP config method on the blade network interface to modify mode to static IP, dhcp and dhcpthenstatic.
                     If this network interface doesn't support DHCP, show 'notApplicable(255)'"
                     ::= { bladeNetworkInterfaceEntry 12 }

         bladeNetworkInterfaceMACAddr OBJECT-TYPE
                     SYNTAX  OCTET STRING
                     MAX-ACCESS  read-only
                     STATUS  current -- was mandatory
                     DESCRIPTION
                     "Show the blade network interface MAC address. If this network interface doesn't support MAC, show 'notApplicable'"
                     ::= { bladeNetworkInterfaceEntry 13 }
-- CIRPAK_MODS END

      
      -- ********************************************************************************
      -- Switch module control and config
      -- ********************************************************************************
      switchModule OBJECT IDENTIFIER ::= { blades 3 }
       -- Server blade switch module control and configuration

       -- ********************************************************************************
       -- Switch module control
       -- ********************************************************************************
       switchModuleControl OBJECT IDENTIFIER ::= { switchModule 1 }
        -- Server blade switch module control

        smControlTable OBJECT-TYPE
                    SYNTAX  SEQUENCE OF SmControlEntry
                    MAX-ACCESS  not-accessible
                    STATUS  current -- was mandatory
                    DESCRIPTION
                    "Switch module control table."
                    ::= { switchModuleControl 1 }

         smControlEntry  OBJECT-TYPE
                       SYNTAX SmControlEntry
                       MAX-ACCESS  not-accessible
                       STATUS  current -- was mandatory
                       DESCRIPTION
                       "Switch module control table entry"
                       INDEX { smControlIndex }
                       ::= { smControlTable 1 }

         SmControlEntry ::= SEQUENCE {
                     smControlIndex INTEGER,
                     switchModuleControlId INTEGER,
                     smPostResultsAvailable INTEGER,
                     smPostResultsValue OCTET STRING,
                     switchModuleMemDiagEnableDisable INTEGER,
                     smCfgCtrlEnableDisable INTEGER,
                     smExtEthPortsEnableDisable INTEGER,
                     switchPingRequest INTEGER,
                     smCfgCtrlOnResetEnableDisable INTEGER,
                     smHealthState INTEGER,
                     smPMState INTEGER,
                     smPMCtrlEnableDisable INTEGER
                     }

         smControlIndex OBJECT-TYPE
                     SYNTAX  Integer32 (0..2147483647) -- was INTEGER
                     MAX-ACCESS  read-only
                     STATUS  current -- was mandatory
                     DESCRIPTION
                     "Switch module control table index."
                     ::= { smControlEntry 1 }

         switchModuleControlId OBJECT-TYPE
                     SYNTAX  INTEGER {
                       module1(1),
                       module2(2),
                       module3(3),
                       module4(4),
                       module5(5),
                       module6(6),
                       module7(7),
                       module8(8),
                       module9(9),
                       module10(10)
                     }
                     MAX-ACCESS  read-only
                     STATUS  current -- was mandatory
                     DESCRIPTION
                     "The switch module numeric identifier."
                     ::= { smControlEntry 2 }

         smPostResultsAvailable OBJECT-TYPE
                     SYNTAX  INTEGER {
                       false(0),
                       true(1)
                     }
                     MAX-ACCESS  read-only
                     STATUS  current -- was mandatory
                     DESCRIPTION
                     "Describes whether the switch module POST diagnostic result
                     value contained in the smPostResultsValue is valid."
                     ::= { smControlEntry 3 }

         smPostResultsValue OBJECT-TYPE
                     SYNTAX  OCTET STRING
                     MAX-ACCESS  read-only
                     STATUS  current -- was mandatory
                     DESCRIPTION
                     "The range of values and meanings are as follows:
                      0x00 - 0x7F  (  0 - 127)  Base internal functions
                      0x80 - 0x9F  (128 - 159)  Internal interface failures
                      0xA0 - 0xAF  (160 - 175)  External interface failures
                      0xB0 - 0xFE  (176 - 254)  Reserved
                      0xFF         (255)        Switch completed POST successfully"
                     ::= { smControlEntry 4 }

         switchModuleMemDiagEnableDisable OBJECT-TYPE
                     SYNTAX  INTEGER {
                       enabled(0),
                       disabled(1)
                     }
                     MAX-ACCESS  read-write
                     STATUS  current -- was mandatory
                     DESCRIPTION
                     "Switch module memory diagnostics enabled or disabled."
                     ::= { smControlEntry 5 }

         smCfgCtrlEnableDisable OBJECT-TYPE
                     SYNTAX  INTEGER {
                       disabled(0),
                       enabled(1)
                     }
                     MAX-ACCESS  read-write
                     STATUS  current -- was mandatory
                     DESCRIPTION
                     "Switch module configuration control.  When set to enabled, only the MM can manage 
                     the module. 
                     This MIB object can not be set, if AMM grants switch module the Protected Mode permission. 
                     This MIB object can not be set, if the switch module is participating in the Stacking Mode
                     and external management is protected.
                     NOTE: This MIB object is not applicable to modules that are running in Network Address 
                     Translation (NAT) Mode."
                     ::= { smControlEntry 6 }

         smExtEthPortsEnableDisable OBJECT-TYPE
                     SYNTAX  INTEGER {
                       disabled(0),
                       enabled(1)
                     }
                     MAX-ACCESS  read-write
                     STATUS  current -- was mandatory
                     DESCRIPTION
                     "Switch module external ethernet ports enabled or disabled.
                      This MIB object can not be set, if AMM grants switch module the 
                      Protected Mode permission.
                      This MIB object can not be set, if the switch module is participating
                      in the Stacking Mode and External Port Access is protected."
                     ::= { smControlEntry 7 }

         switchPingRequest OBJECT-TYPE
                     SYNTAX  INTEGER {
                       execute(1)
                     }
                     MAX-ACCESS  read-write
                     STATUS  current -- was mandatory
                     DESCRIPTION
                     "Sends a ping to a switch module's current IP address.
                      This MIB object can not be set, if AMM grants switch module the Protected Mode 
                     permission and switch module goes into Protected Mode.
                     This MIB object can not be set, if the switch module is participating 
                     in the Stacking Mode and IP Configuration is protected.
                     NOTE: Value returned for the GET command is meaningless 
                     for this MIB object."
                     ::= { smControlEntry 8 }

         smCfgCtrlOnResetEnableDisable OBJECT-TYPE
                     SYNTAX  INTEGER {
                       enabled(0),
                       disabled(1)
                     }
                     MAX-ACCESS  read-write
                     STATUS  current -- was mandatory
                     DESCRIPTION
                     "Switch module configuration control on resets (default and unsolicited).  
                     When set to enabled, the factory default IP configuration will become 
                     active when the I/O module is reset to factory defaults by either the
                     management module or the I/O module. If an I/O module reset is initiated
                     by a source other than the management module then the previous IP configuration
                     will be in affect. In both these cases the MM will lose IP communications with 
                     the IOM.
                     This MIB object can not be set, if AMM grants switch module the Protected Mode 
                     permission and switch module goes into Protected Mode.
                     NOTE: This MIB object is not applicable to modules that are running in Network Address 
                     Translation (NAT) Mode."
                     ::= { smControlEntry 9 }

         smHealthState OBJECT-TYPE
                     SYNTAX  INTEGER {
                       unknown(0),
                       good(1),
                       warning(2),
                       bad(3)
                     }
                     MAX-ACCESS  read-only
                     STATUS  current -- was mandatory
                     DESCRIPTION
                     "The health state for the switch module.
                     0 = unknown, 1 = good, 2 = warning, 3 = bad."
                     ::= { smControlEntry 15}

        smPMState OBJECT-TYPE
                     SYNTAX  INTEGER {
                       standby(0),
                       pending(1),
                       attention(2),
                       active(3),
                       notApplicable(255)
                     }
                     MAX-ACCESS  read-only
                     STATUS  current -- was mandatory
                     DESCRIPTION
                     "The Protected Mode Status for the switch module.
                     standby- Protected Mode capability exists on the IOM but has not 
                     been activated on the switch module or the AMM.
                     pending - Protected Mode has been activated on the AMM but not yet on the switch module.
                     active - Protected Mode is active on both the switch module and the AMM.
                     attention - Protected Mode is enabled on the switch module but not on the AMM.
                     NOTE: The term disabled was changed to the term standby to be more descriptive."
                     ::= { smControlEntry 16}

        smPMCtrlEnableDisable OBJECT-TYPE
                     SYNTAX  INTEGER {
                       disabled(0),
                       enabled(1)
                     }
                     MAX-ACCESS  read-write
                     STATUS  current -- was mandatory
                     DESCRIPTION
                     "AMM Protected Mode permission for the switch module.
                     disabled - allow AMM to disable Protected Mode Permission for the switch module.
                     enabled - allow AMM to grant Protected Mode Permission for the switch module."
                     ::= { smControlEntry 17}

        smPowerRestartTable OBJECT-TYPE
                    SYNTAX  SEQUENCE OF SmPowerRestartEntry
                    MAX-ACCESS  not-accessible
                    STATUS  current -- was mandatory
                    DESCRIPTION
                    "Switch module power restart table."
                    ::= { switchModuleControl 7 }

         smPowerRestartEntry  OBJECT-TYPE
                       SYNTAX SmPowerRestartEntry
                       MAX-ACCESS  not-accessible
                       STATUS  current -- was mandatory
                       DESCRIPTION
                       "Switch module power restart table entry"
                       INDEX { smPowerRestartIndex }
                       ::= { smPowerRestartTable 1 }

         SmPowerRestartEntry ::= SEQUENCE {
                     smPowerRestartIndex INTEGER,
                     smPowerRestartId INTEGER,
                     smSwitchExists INTEGER,
                     smSwitchType INTEGER,
                     smMACAddress OCTET STRING,
                     smIPAddress IpAddress,
                     switchModulePowerOnOff INTEGER,
                     smReset INTEGER,
                     smResetToDefault INTEGER,
                     smRestartAndRunStdDiag INTEGER,
                     smRestartAndRunExtDiag INTEGER,
                     smRestartAndRunFullDiag INTEGER,
                     smSwitchSubType INTEGER,
                     smSwitchWidth INTEGER,
                     smManufacturingID OCTET STRING,
                     smStackingModeState INTEGER,
                     smStackingModeInfo OCTET STRING
                     }

         smPowerRestartIndex OBJECT-TYPE
                     SYNTAX  Integer32 (0..2147483647) -- was INTEGER
                     MAX-ACCESS  read-only
                     STATUS  current -- was mandatory
                     DESCRIPTION
                     "Switch module power restart index."
                     ::= { smPowerRestartEntry 1 }

         smPowerRestartId OBJECT-TYPE
                     SYNTAX  INTEGER {
                       module1(1),
                       module2(2),
                       module3(3),
                       module4(4),
                       module5(5),
                       module6(6),
                       module7(7),
                       module8(8),
                       module9(9),
                       module10(10)
                     }
                     MAX-ACCESS  read-only
                     STATUS  current -- was mandatory
                     DESCRIPTION
                     "The switch module numeric identifier."
                     ::= { smPowerRestartEntry 2 }

         smSwitchExists OBJECT-TYPE
                     SYNTAX  INTEGER {
                       false(0),
                       true(1)
                     }
                     MAX-ACCESS  read-only
                     STATUS  current -- was mandatory
                     DESCRIPTION
                     "Indicates whether the switch module specified exists or not."
                     ::= { smPowerRestartEntry 3 }

         smSwitchType OBJECT-TYPE
                     SYNTAX  INTEGER {
                       unknown(0),
                       ethernet(1),
                       fibre(2),
                       opm(3),
                       serialCM(4),
                       copperPassThrough(5),
                       infiniband(6), 
                       highSpeed(20),
                       passThrough(30),
                       sas(40)
                     }
                     MAX-ACCESS  read-only
                     STATUS  current -- was mandatory
                     DESCRIPTION
                     "Switch module type."
                     ::= { smPowerRestartEntry 4 }

         smMACAddress OBJECT-TYPE
                     SYNTAX  OCTET STRING
                     MAX-ACCESS  read-only
                     STATUS  current -- was mandatory
                     DESCRIPTION
                     "Switch module MAC address."
                     ::= { smPowerRestartEntry 5 }

         smIPAddress OBJECT-TYPE
                     SYNTAX  IpAddress
                     MAX-ACCESS  read-only
                     STATUS  current -- was mandatory
                     DESCRIPTION
                     "The switch module current IP address.
                     If the switch module is participating in the Stacking Mode
                     and IP Configuration is protected, then the stack management 
                     IP address is displayed."
                     ::= { smPowerRestartEntry 6 }

         switchModulePowerOnOff OBJECT-TYPE
                     SYNTAX  INTEGER {
                       poweroff(0),
                       poweron(1),
                       shutdownInProgress(2)
                     }
                     MAX-ACCESS  read-write
                     STATUS  current -- was mandatory
                     DESCRIPTION
                     "I/O Module power on or power off.  If powering on a currently
                     powered off I/O Module, then the I/O Module will execute a POST.
                     The results of this POST will need to be retrieved using the 'Post Results'
                     command.  
                     NOTE:
                     When powering off a currently powered on I/O Module, a minimum of 1 second
                     is needed to allow the module to power off before powering back on.
                     The value 'shutdownInProgress' is for I/O Modules that may take some time to 
                     transition from 'poweron' to 'poweroff'.  For example, SAS Controller Modules must 
                     flush pending I/O before powering off in order to maintain data integrity.
                     The value'shutdownInProgress' can not be used to set.
                     If both SAS Controller Module and SAS Connectivity Module are installed in slot 3 
                     and 4 of BCS chassis, AMM must prevent one of them from powering on otherwise 
                     there would be conflict with the Storage Module access and possibly corruption of data.
                     This MIB object can not be set, if AMM grants the I/O Module the Protected Mode
                     permission and module goes into Protected Mode."
                     ::= { smPowerRestartEntry 7 }

         smReset OBJECT-TYPE
                     SYNTAX  INTEGER {
                       execute(1)
                     }
                     MAX-ACCESS  read-write
                     STATUS  current -- was mandatory
                     DESCRIPTION
                     "For the case where the switch module is currently powered on, this command
                     will effectively power off and then power on the switch module indicated and
                     cause it to run its POST test.  For the case where the switch module is
                     currently powered off, the command will just power on the switch module.
                     This MIB object can not be set, if AMM grants switch module the Protected Mode 
                     permission and switch module goes into Protected Mode.
                     NOTE: Value returned for the GET command is meaningless for this MIB object."
                     ::= { smPowerRestartEntry 8 }

         smResetToDefault OBJECT-TYPE
                     SYNTAX  INTEGER {
                       execute(1)
                     }
                     MAX-ACCESS  read-write
                     STATUS  current -- was mandatory
                     DESCRIPTION
                     "For the case where the switch module is currently powered on, this command
                     will effectively power off and then power on the switch module indicated and
                     cause it to run its POST test.  For the case where the switch module is
                     currently powered off, the command will just power on the switch module.
                     In both cases, the switch module will reset the configuration to the default
                     values.
                     This MIB object can not be set, if AMM grants switch module the Protected Mode 
                     permission and switch module goes into Protected Mode.
                     This MIB object can not be set, if the switch module is participating in the 
                     Stacking Mode and reset to default is protected.
                     NOTE: Value returned for the GET command is meaningless for this MIB object."
                     ::= { smPowerRestartEntry 9 }

         smRestartAndRunStdDiag OBJECT-TYPE
                     SYNTAX  INTEGER {
                       execute(1)
                     }
                     MAX-ACCESS  read-write
                     STATUS  current -- was mandatory
                     DESCRIPTION
                     "To power cycle the selected module(s) and then run the standard diagnostic 
                     test package.  
                     
                     NOTE: Value returned for the GET command is meaningless for this MIB object."
                     ::= { smPowerRestartEntry 10 }

         smRestartAndRunExtDiag OBJECT-TYPE
                     SYNTAX  INTEGER {
                       execute(1)
                     }
                     MAX-ACCESS  read-write
                     STATUS  current -- was mandatory
                     DESCRIPTION
                     "To power cycle the selected module(s) and then run the extended diagnostic 
                     test package. This option is not supported on all I/O modules.
                     
                     NOTE: Value returned for the GET command is meaningless for this MIB object."
                     ::= { smPowerRestartEntry 11 }

         smRestartAndRunFullDiag OBJECT-TYPE
                     SYNTAX  INTEGER {
                       execute(1)
                     }
                     MAX-ACCESS  read-write
                     STATUS  current -- was mandatory
                     DESCRIPTION
                     "To power cycle the selected module(s) and then run the full diagnostic test 
                     package. The full diagnostic test package may take over 5 minutes to run. 
                     This option is not supported on all I/O modules.
                     
                     NOTE: Value returned for the GET command is meaningless for this MIB object."
                     ::= { smPowerRestartEntry 12 }

         smSwitchSubType OBJECT-TYPE
                     SYNTAX  INTEGER {
                       unknown(0),
                       ethernet(1),
                       fibre(2),
                       infiniband(6),
                       sas(7),
                       raidsas(8),
                       icpm(9)
                     }
                     MAX-ACCESS  read-only
                     STATUS  current -- was mandatory
                     DESCRIPTION
                     "Switch module subtype.   
                     NOTE: Some Legacy modules do not support a subtype and will be displayed as unknown."
                     ::= { smPowerRestartEntry 20 }

         smSwitchWidth OBJECT-TYPE
                     SYNTAX  INTEGER
                     MAX-ACCESS  read-only
                     STATUS  current -- was mandatory
                     DESCRIPTION
                     "Switch module width."
                     ::= { smPowerRestartEntry 21 }
                     
        smManufacturingID OBJECT-TYPE
                      SYNTAX  OCTET STRING
                      MAX-ACCESS  read-only
                      STATUS  current -- was mandatory
                      DESCRIPTION
                      "Switch module hardware VPD manufacturing ID."
                      ::= { smPowerRestartEntry 22 }

        smStackingModeState OBJECT-TYPE
                     SYNTAX  INTEGER {
                       standby(0),
                       member(1),
                       master(2),
                       notApplicable(255)
                     }
                     MAX-ACCESS  read-only
                     STATUS  current -- was mandatory
                     DESCRIPTION
                     "The Stacking Mode Status for the switch module.
                     standby - I/O module has stacking capability but is not part of a stack.
                     member - I/O module has stacking capability and is part of a stack in the
                       member role.
                     master - I/O module has stacking capability and is part of a stack in the
                       master role.
                     NOTE: The term disabled was changed to the term standby to be more descriptive."
                     ::= { smPowerRestartEntry 23 }

        smStackingModeInfo OBJECT-TYPE
                    SYNTAX OCTET STRING
                    MAX-ACCESS read-only
                    STATUS current -- was mandatory
                    DESCRIPTION
                    "A string containing a text description about the details of which functions are
                    protected for a switch module when it is in Stacking Mode as Master or Member. 
                    The possible functions protected by switch modules are IP configuration, 
                    External Port Access, External Management all over ports and Restore to defaults."
                    ::= { smPowerRestartEntry 24 }


                     
       -- ********************************************************************************
       -- Switch module config
       -- ********************************************************************************
       switchModuleConfig OBJECT IDENTIFIER ::= { switchModule 2 }
        -- Server blade switch module configuration

        switchMgmtNetworkCfg OBJECT IDENTIFIER ::= { switchModuleConfig 1 }
         -- Server blade switch module management network config

         -- 
         -- Current switch module network config
         -- 
         switchCurrentNwCfg OBJECT IDENTIFIER ::= { switchMgmtNetworkCfg 1 }
          -- Server blade switch module current network config

          smCurrentIPInfoTable OBJECT-TYPE
                      SYNTAX  SEQUENCE OF SmCurrentIPInfoEntry
                      MAX-ACCESS  not-accessible
                      STATUS  current -- was mandatory
                      DESCRIPTION
                      "Switch module current IP information.
                      
                      NOTE: This MIB object is not applicable to modules that are running in  
                      Stacking Mode and IP configuration is protected."
                      ::= { switchCurrentNwCfg 1 }

           smCurrentIPInfoEntry  OBJECT-TYPE
                         SYNTAX SmCurrentIPInfoEntry
                         MAX-ACCESS  not-accessible
                         STATUS  current -- was mandatory
                         DESCRIPTION
                         "Switch module current IP table entry.
                      
                         NOTE: This MIB object is not applicable to modules that are running in  
                         Stacking Mode and IP configuration is protected."
                         INDEX { smCurrentIPInfoIndex }
                         ::= { smCurrentIPInfoTable 1 }

           SmCurrentIPInfoEntry ::= SEQUENCE {
                       smCurrentIPInfoIndex INTEGER,
                       smCurrentIPInfoId INTEGER,
                       smCurrentIPInfoExists INTEGER,
                       smCurrentIPInfoPowerState INTEGER,
                       smCurrentIPAddr IpAddress,
                       smCurrentSubnetMask IpAddress,
                       smCurrentGateway IpAddress,
                       smCurrentIPConfigMethod INTEGER
                       }

           smCurrentIPInfoIndex OBJECT-TYPE
                       SYNTAX  Integer32 (0..2147483647) -- was INTEGER
                       MAX-ACCESS  read-only
                       STATUS  current -- was mandatory
                       DESCRIPTION
                       "Switch module current IP info index.

                        NOTE: This MIB object is not applicable to modules that are running in  
                        Stacking Mode and IP configuration is protected."
                       ::= { smCurrentIPInfoEntry 1 }

           smCurrentIPInfoId OBJECT-TYPE
                       SYNTAX  INTEGER {
                         module1(1),
                         module2(2),
                         module3(3),
                         module4(4),
                         module5(5),
                         module6(6),
                         module7(7),
                         module8(8),
                         module9(9),
                         module10(10)
                       }
                       MAX-ACCESS  read-only
                       STATUS  current -- was mandatory
                       DESCRIPTION
                       "The switch module numeric identifier.

                        NOTE: This MIB object is not applicable to modules that are running in  
                        Stacking Mode and IP configuration is protected."
                       ::= { smCurrentIPInfoEntry 2 }

           smCurrentIPInfoExists OBJECT-TYPE
                       SYNTAX  INTEGER {
                         false(0),
                         true(1)
                       }
                       MAX-ACCESS  read-only
                       STATUS  current -- was mandatory
                       DESCRIPTION
                       "Indicates whether the switch module specified exists or not.

                        NOTE: This MIB object is not applicable to modules that are running in  
                        Stacking Mode and IP configuration is protected."
                       ::= { smCurrentIPInfoEntry 3 }

           smCurrentIPInfoPowerState OBJECT-TYPE
                       SYNTAX  INTEGER {
                         off(0),
                         on(1),
                         shutdownInProgress(2)
                       }
                       MAX-ACCESS  read-only
                       STATUS  current -- was mandatory
                       DESCRIPTION
                       "Indicates whether the I/O Module specified is powered on or not.
                        The value 'shutdownInProgress' is for the I/O Module that may take some time to 
                        transition from 'poweron' to 'poweroff'. Such as SAS Controller Modules, that must 
                        flush pending I/O before powering off in order to maintain data integrity.

                        NOTE: This MIB object is not applicable to modules that are running in  
                        Stacking Mode and IP configuration is protected."
                       ::= { smCurrentIPInfoEntry 4 }

           smCurrentIPAddr OBJECT-TYPE
                        SYNTAX  IpAddress
                        MAX-ACCESS  read-only
                        STATUS  current -- was mandatory
                        DESCRIPTION
                        "The switch module current IP address.

                         NOTE: This MIB object is not applicable to modules that are running in  
                         Stacking Mode and IP configuration is protected."
                        ::= { smCurrentIPInfoEntry 6 }


           smCurrentSubnetMask OBJECT-TYPE
                        SYNTAX  IpAddress
                        MAX-ACCESS  read-only
                        STATUS  current -- was mandatory
                        DESCRIPTION
                        "The switch module current subnet mask.

                         NOTE: This MIB object is not applicable to modules that are running in  
                         Stacking Mode and IP configuration is protected."
                        ::= { smCurrentIPInfoEntry 7 }

          smCurrentGateway OBJECT-TYPE
                       SYNTAX  IpAddress
                       MAX-ACCESS  read-only
                       STATUS  current -- was mandatory
                       DESCRIPTION
                       "The switch module current IP gateway.

                        NOTE: This MIB object is not applicable to modules that are running in  
                        Stacking Mode and IP configuration is protected."
                       ::= { smCurrentIPInfoEntry 8 }

          smCurrentIPConfigMethod OBJECT-TYPE
                       SYNTAX  INTEGER {
                         unknown(0),
                         static(1),
                         dhcp(2),
                         nat (3), 
                         bootp(4)
                       }
                       MAX-ACCESS  read-only
                       STATUS  current -- was mandatory
                       DESCRIPTION
                       "The switch module current IP configuration method.

                        NOTE: This MIB object is not applicable to modules that are running in  
                        Stacking Mode and IP configuration is protected."
                       ::= { smCurrentIPInfoEntry 9 }


         -- ********************************************************************************
         -- New switch module network config
         -- ********************************************************************************
         switchNewNwCfg OBJECT IDENTIFIER ::= { switchMgmtNetworkCfg 2 }
          -- Server blade switch module new network config

          smNewIPInfoTable OBJECT-TYPE
                      SYNTAX  SEQUENCE OF SmNewIPInfoEntry
                      MAX-ACCESS  not-accessible
                      STATUS  current -- was mandatory
                      DESCRIPTION
                      "Switch module new IP information.
                      
                       NOTE: This MIB object is not applicable to modules that are running in Network Address 
                       Translation (NAT) Mode or Stacking Mode and IP configuration is protected."
                      ::= { switchNewNwCfg 1 }

           smNewIPInfoEntry  OBJECT-TYPE
                         SYNTAX SmNewIPInfoEntry
                         MAX-ACCESS  not-accessible
                         STATUS  current -- was mandatory
                         DESCRIPTION
                         "Switch module new IP configuration information table entry.  
                         
                         NOTE: This MIB table is not applicable to modules that are running in Network Address 
                         Translation (NAT) Mode or Stacking Mode and IP configuration is protected."
                         INDEX { smNewIPInfoIndex }
                         ::= { smNewIPInfoTable 1 }

           SmNewIPInfoEntry ::= SEQUENCE {
                       smNewIPInfoIndex INTEGER,
                       smNewIPInfoId INTEGER,
                       smNewIPInfoExists INTEGER,
                       smNewIPInfoPowerState INTEGER,
                       smNewIPAddr IpAddress,
                       smNewSubnetMask IpAddress,
                       smNewGateway IpAddress,
                       smNewIPConfigMethod INTEGER,
                       smNewIPConfigEnableDisable INTEGER
                       }

           smNewIPInfoIndex OBJECT-TYPE
                       SYNTAX  Integer32 (0..2147483647) -- was INTEGER
                       MAX-ACCESS  read-only
                       STATUS  current -- was mandatory
                       DESCRIPTION
                       "Switch module new IP info index.  
                       
                       NOTE: This MIB object is not applicable to modules that are running in Network Address 
                       Translation (NAT) Mode or Stacking Mode and IP configuration is protected."
                       ::= { smNewIPInfoEntry 1 }

           smNewIPInfoId OBJECT-TYPE
                       SYNTAX  INTEGER {
                         module1(1),
                         module2(2),
                         module3(3),
                         module4(4),
                         module5(5),
                         module6(6),
                         module7(7),
                         module8(8),
                         module9(9),
                         module10(10)
                       }
                       MAX-ACCESS  read-only
                       STATUS  current -- was mandatory
                       DESCRIPTION
                       "The switch module numeric identifier.  
                       
                       NOTE: This MIB object is not applicable to modules that are running in Network Address 
                       Translation (NAT) Mode or Stacking Mode and IP configuration is protected."
                       ::= { smNewIPInfoEntry 2 }

           smNewIPInfoExists OBJECT-TYPE
                       SYNTAX  INTEGER {
                         false(0),
                         true(1)
                       }
                       MAX-ACCESS  read-only
                       STATUS  current -- was mandatory
                       DESCRIPTION
                       "Indicates whether the switch module specified exists or not.  
                       
                       NOTE: This MIB object is not applicable to modules that are running in Network Address 
                       Translation (NAT) Mode or Stacking Mode and IP configuration is protected."
                       ::= { smNewIPInfoEntry 3 }

           smNewIPInfoPowerState OBJECT-TYPE
                       SYNTAX  INTEGER {
                         off(0),
                         on(1)
                       }
                       MAX-ACCESS  read-only
                       STATUS  current -- was mandatory
                       DESCRIPTION
                       "Indicates whether the switch module specified is powered on or not.  
                       
                       NOTE: This MIB object is not applicable to modules that are running in Network Address 
                       Translation (NAT) Mode or Stacking Mode and IP configuration is protected.."
                       ::= { smNewIPInfoEntry 4 }

           smNewIPAddr OBJECT-TYPE
                        SYNTAX  IpAddress
                        MAX-ACCESS  read-write
                        STATUS  current -- was mandatory
                        DESCRIPTION
                        "The switch module new IP address.  Before setting this object to a new value, 
                        smNewIpconfigEnableDisable object must first be set to disabled.
                        NOTE: This MIB object can not be set if the AMM grants the switch module Protected Mode 
                        permission and the switch module goes into Protected Mode. 
                        NOTE: This MIB object can not be set if the switch module is in Stacking Mode
                        and IP Configuration is protected.
                        NOTE: This MIB object is not applicable to modules that are running in Network Address 
                        Translation (NAT) Mode."
                        ::= { smNewIPInfoEntry 6 }


           smNewSubnetMask OBJECT-TYPE
                        SYNTAX  IpAddress
                        MAX-ACCESS  read-write
                        STATUS  current -- was mandatory
                        DESCRIPTION
                        "The switch module new subnet mask.  Before setting this object to a new value, 
                        smNewIpconfigEnableDisable object must first be set to disabled.
                        NOTE: This MIB object can not be set if the AMM grants the switch module Protected Mode 
                        permission and the switch module goes into Protected Mode.
                        NOTE: This MIB object can not be set if the switch module is in Stacking Mode,
                        and IP Configuration is protected.
                        NOTE: This MIB object is not applicable to modules that are running in Network Address 
                        Translation (NAT) Mode."
                        ::= { smNewIPInfoEntry 7 }

           smNewGateway OBJECT-TYPE
                        SYNTAX  IpAddress
                        MAX-ACCESS  read-write
                        STATUS  current -- was mandatory
                        DESCRIPTION
                        "The switch module new IP gateway.  Before setting this object to a new value, 
                        smNewIpconfigEnableDisable object must first be set to disabled.
                        NOTE: This MIB object can not be set if the AMM grants the switch module Protected Mode 
                        permission and the switch module goes into Protected Mode.
                        NOTE: This MIB object can not be set if the switch module is in Stacking Mode,
                        and IP Configuration is protected.
                        NOTE: This MIB object is not applicable to modules that are running in Network Address 
                        Translation (NAT) Mode."
                        ::= { smNewIPInfoEntry 8 }

           smNewIPConfigMethod OBJECT-TYPE
                        SYNTAX  INTEGER {
                          unknown(0),
                          static(1),
                          dhcp(2),
                          nat(3), 
                          bootp(4)
                        }
                        MAX-ACCESS  read-write
                        STATUS  current -- was mandatory
                        DESCRIPTION
                        "The switch module new IP configuration method.  Before setting this object to a new value, 
                        smNewIpconfigEnableDisable object must first be set to disabled.
                        NOTE: This MIB object can not be set if the AMM grants the switch module Protected Mode 
                        permission and the switch module goes into Protected Mode.
                        NOTE: This MIB object can not be set if the switch module is in Stacking Mode,
                        and IP Configuration is protected.
                        NOTE: This MIB object is not applicable to modules that are running in Network Address 
                        Translation (NAT) Mode."
                        ::= { smNewIPInfoEntry 9 }

           smNewIPConfigEnableDisable OBJECT-TYPE
                       SYNTAX  INTEGER {
                         disable(0),
                         enable(1)
                       }
                       MAX-ACCESS  read-write
                       STATUS  current -- was mandatory
                       DESCRIPTION
                       "A set command enables a new IP configuration that has been
                       previously defined.  A get command indicates whether the new
                       IP configuration information has been enabled.  
                       NOTE: This MIB object can not be set if the AMM grants the switch module Protected Mode 
                       permission and the switch module goes into Protected Mode.
                       NOTE: This MIB object can not be set if the switch module is in Stacking Mode,
                       and IP Configuration is protected.
                       NOTE: This MIB object is not applicable to modules that are running in Network Address 
                       Translation (NAT) Mode."
                       ::= { smNewIPInfoEntry 10 }


         -- ********************************************************************************
         -- Network protocol (Network Address Translation) config
         -- ********************************************************************************
         switchNwProtCfg OBJECT IDENTIFIER ::= { switchMgmtNetworkCfg 3 }

         switchNwProtCfgModOne  OBJECT IDENTIFIER ::= { switchNwProtCfg 1 }
         
          smNwProtInfoModOneTable OBJECT-TYPE
                      SYNTAX  SEQUENCE OF SmNwProtInfoModOneEntry
                      MAX-ACCESS  not-accessible
                      STATUS  current -- was mandatory
                      DESCRIPTION
                      "Switch module 1 network protocol (Network Address Translation) information."
                      ::= { switchNwProtCfgModOne 1 }

           smNwProtInfoModOneEntry  OBJECT-TYPE
                         SYNTAX SmNwProtInfoModOneEntry
                         MAX-ACCESS  not-accessible
                         STATUS  current -- was mandatory
                         DESCRIPTION
                         "Switch module 1 network protocol (Network Address Translation) configuration 
                         information table entry"
                         INDEX { smNwProtInfoModOneIndex }
                         ::= { smNwProtInfoModOneTable 1 }

           SmNwProtInfoModOneEntry ::= SEQUENCE {
                       smNwProtInfoModOneIndex INTEGER,
                       smNwProtInfoModOneId INTEGER,
                       smNwProtInfoModOneExists INTEGER,
                       smNwProtInfoModOnePowerState INTEGER,
                       smNwProtInfoModOneProtName OCTET STRING,
                       smNwProtInfoModOneProtID INTEGER,
                       smNwProtInfoModOneExtPort INTEGER,
                       smNwProtInfoModOneIntPort INTEGER,
                       smNwProtInfoModOneEnable INTEGER
                       }
           
           smNwProtInfoModOneIndex OBJECT-TYPE
                       SYNTAX  Integer32 (0..2147483647) -- was INTEGER
                       MAX-ACCESS  read-only
                       STATUS  current -- was mandatory
                       DESCRIPTION
                       "Switch module 1 network protocol (Network Address Translation) information index."
                       ::= { smNwProtInfoModOneEntry 1 }

           smNwProtInfoModOneId OBJECT-TYPE
                       SYNTAX  INTEGER {
                         module1(1),
                         module2(2),
                         module3(3),
                         module4(4),
                         module5(5),
                         module6(6),
                         module7(7),
                         module8(8),
                         module9(9),
                         module10(10)
                       }
                       MAX-ACCESS  read-only
                       STATUS  current -- was mandatory
                       DESCRIPTION
                       "The switch module 1 numeric identifier."
                       ::= { smNwProtInfoModOneEntry 2 }

           smNwProtInfoModOneExists OBJECT-TYPE
                       SYNTAX  INTEGER {
                         false(0),
                         true(1)
                       }
                       MAX-ACCESS  read-only
                       STATUS  current -- was mandatory
                       DESCRIPTION
                       "Indicates whether the switch module 1 exists or not."
                       ::= { smNwProtInfoModOneEntry 3 }

           smNwProtInfoModOnePowerState OBJECT-TYPE
                       SYNTAX  INTEGER {
                         off(0),
                         on(1)
                       }
                       MAX-ACCESS  read-only
                       STATUS  current -- was mandatory
                       DESCRIPTION
                       "Indicates whether the switch module 1 is powered on or not."
                       ::= { smNwProtInfoModOneEntry 4 }

           smNwProtInfoModOneProtName OBJECT-TYPE
                        SYNTAX  OCTET STRING
                        MAX-ACCESS  read-write
                        STATUS  current -- was mandatory
                        DESCRIPTION
                        "Protocol name"
                        ::= { smNwProtInfoModOneEntry 5 }

           smNwProtInfoModOneProtID OBJECT-TYPE
                        SYNTAX  INTEGER {
                          -- ip(1),
                          tcp(2), 
                          udp(3)
                        }
                        MAX-ACCESS  read-write
                        STATUS  current -- was mandatory
                        DESCRIPTION
                        "Protocol ID"
                        ::= { smNwProtInfoModOneEntry 6 }

           smNwProtInfoModOneExtPort OBJECT-TYPE
                        SYNTAX  INTEGER
                        MAX-ACCESS  read-write
                        STATUS  current -- was mandatory
                        DESCRIPTION
                        "External port"
                        ::= { smNwProtInfoModOneEntry 7 }

           smNwProtInfoModOneIntPort OBJECT-TYPE
                        SYNTAX  INTEGER 
                        MAX-ACCESS  read-write
                        STATUS  current -- was mandatory
                        DESCRIPTION
                        "Internal port."
                        ::= { smNwProtInfoModOneEntry 8 }

           smNwProtInfoModOneEnable OBJECT-TYPE
                       SYNTAX  INTEGER {
                         disable(0),
                         enable(1)
                       }
                       MAX-ACCESS  read-write
                       STATUS  current -- was mandatory
                       DESCRIPTION
                       "Enable or disable the protocol entry."
                       ::= { smNwProtInfoModOneEntry 9 }
           
           smNwProtInfoModOneActivate OBJECT-TYPE
                       SYNTAX  INTEGER {
                         execute(1)
                       }
                       MAX-ACCESS  read-write
                       STATUS  current -- was mandatory
                       DESCRIPTION
                       "Activate all network protocol settings for the switch module.
                       NOTE: Value returned for the GET command is meaningless for this MIB object." 
                        ::= { switchNwProtCfgModOne 2 }
           
           smNwProtInfoModOneReset OBJECT-TYPE
                       SYNTAX  INTEGER {
                         execute(1)
                       }
                       MAX-ACCESS  read-write
                       STATUS  current -- was mandatory
                       DESCRIPTION
                       "Reset all network protocol settings for the switch module to default.
                       NOTE: Value returned for the GET command is meaningless for this MIB object." 
                       ::= {  switchNwProtCfgModOne 3 }

         
         switchNwProtCfgModTwo  OBJECT IDENTIFIER ::= { switchNwProtCfg 2 }
         
          smNwProtInfoModTwoTable OBJECT-TYPE
                      SYNTAX  SEQUENCE OF SmNwProtInfoModTwoEntry
                      MAX-ACCESS  not-accessible
                      STATUS  current -- was mandatory
                      DESCRIPTION
                      "Switch module 2 network protocol (Network Address Translation) information."
                      ::= { switchNwProtCfgModTwo 1 }

           smNwProtInfoModTwoEntry  OBJECT-TYPE
                         SYNTAX SmNwProtInfoModTwoEntry
                         MAX-ACCESS  not-accessible
                         STATUS  current -- was mandatory
                         DESCRIPTION
                         "Switch module 2 network protocol (Network Address Translation) configuration 
                         information table entry"
                         INDEX { smNwProtInfoModTwoIndex }
                         ::= { smNwProtInfoModTwoTable 1 }

           SmNwProtInfoModTwoEntry ::= SEQUENCE {
                       smNwProtInfoModTwoIndex INTEGER,
                       smNwProtInfoModTwoId INTEGER,
                       smNwProtInfoModTwoExists INTEGER,
                       smNwProtInfoModTwoPowerState INTEGER,
                       smNwProtInfoModTwoProtName OCTET STRING,
                       smNwProtInfoModTwoProtID INTEGER,
                       smNwProtInfoModTwoExtPort INTEGER,
                       smNwProtInfoModTwoIntPort INTEGER,
                       smNwProtInfoModTwoEnable INTEGER
                       }
           
           smNwProtInfoModTwoIndex OBJECT-TYPE
                       SYNTAX  Integer32 (0..2147483647) -- was INTEGER
                       MAX-ACCESS  read-only
                       STATUS  current -- was mandatory
                       DESCRIPTION
                       "Switch module 2 network protocol (Network Address Translation) information index."
                       ::= { smNwProtInfoModTwoEntry 1 }

           smNwProtInfoModTwoId OBJECT-TYPE
                       SYNTAX  INTEGER {
                         module1(1),
                         module2(2),
                         module3(3),
                         module4(4),
                         module5(5),
                         module6(6),
                         module7(7),
                         module8(8),
                         module9(9),
                         module10(10)
                       }
                       MAX-ACCESS  read-only
                       STATUS  current -- was mandatory
                       DESCRIPTION
                       "The switch module 2 numeric identifier."
                       ::= { smNwProtInfoModTwoEntry 2 }

           smNwProtInfoModTwoExists OBJECT-TYPE
                       SYNTAX  INTEGER {
                         false(0),
                         true(1)
                       }
                       MAX-ACCESS  read-only
                       STATUS  current -- was mandatory
                       DESCRIPTION
                       "Indicates whether the switch module 2 exists or not."
                       ::= { smNwProtInfoModTwoEntry 3 }

           smNwProtInfoModTwoPowerState OBJECT-TYPE
                       SYNTAX  INTEGER {
                         off(0),
                         on(1)
                       }
                       MAX-ACCESS  read-only
                       STATUS  current -- was mandatory
                       DESCRIPTION
                       "Indicates whether the switch module 2 is powered on or not."
                       ::= { smNwProtInfoModTwoEntry 4 }

           smNwProtInfoModTwoProtName OBJECT-TYPE
                        SYNTAX  OCTET STRING
                        MAX-ACCESS  read-write
                        STATUS  current -- was mandatory
                        DESCRIPTION
                        "Protocol name"
                        ::= { smNwProtInfoModTwoEntry 5 }

           smNwProtInfoModTwoProtID OBJECT-TYPE
                        SYNTAX  INTEGER {
                          tcp(2), 
                          udp(3)
                        }  
                        MAX-ACCESS  read-write
                        STATUS  current -- was mandatory
                        DESCRIPTION
                        "Protocol ID"
                        ::= { smNwProtInfoModTwoEntry 6 }

           smNwProtInfoModTwoExtPort OBJECT-TYPE
                        SYNTAX  INTEGER
                        MAX-ACCESS  read-write
                        STATUS  current -- was mandatory
                        DESCRIPTION
                        "External port"
                        ::= { smNwProtInfoModTwoEntry 7 }

           smNwProtInfoModTwoIntPort OBJECT-TYPE
                        SYNTAX  INTEGER 
                        MAX-ACCESS  read-write
                        STATUS  current -- was mandatory
                        DESCRIPTION
                        "Internal port."
                        ::= { smNwProtInfoModTwoEntry 8 }

           smNwProtInfoModTwoEnable OBJECT-TYPE
                       SYNTAX  INTEGER {
                         disable(0),
                         enable(1)
                       }
                       MAX-ACCESS  read-write
                       STATUS  current -- was mandatory
                       DESCRIPTION
                       "Enable or disable the protocol entry."
                       ::= { smNwProtInfoModTwoEntry 9 }
           
           smNwProtInfoModTwoActivate OBJECT-TYPE
                       SYNTAX  INTEGER {
                         execute(1)
                       }
                       MAX-ACCESS  read-write
                       STATUS  current -- was mandatory
                       DESCRIPTION
                       "Activate all network protocol settings for the switch module.
                       NOTE: Value returned for the GET command is meaningless for this MIB object." 
                       ::= { switchNwProtCfgModTwo 2 }
           
           smNwProtInfoModTwoReset OBJECT-TYPE
                       SYNTAX  INTEGER {
                         execute(1)
                       }
                       MAX-ACCESS  read-write
                       STATUS  current -- was mandatory
                       DESCRIPTION
                       "Reset all network protocol settings for the switch module to default.
                       NOTE: Value returned for the GET command is meaningless for this MIB object." 
                       ::= { switchNwProtCfgModTwo 3 }


         switchNwProtCfgModThree  OBJECT IDENTIFIER ::= { switchNwProtCfg 3 }
         
          smNwProtInfoModThreeTable OBJECT-TYPE
                      SYNTAX  SEQUENCE OF SmNwProtInfoModThreeEntry
                      MAX-ACCESS  not-accessible
                      STATUS  current -- was mandatory
                      DESCRIPTION
                      "Switch module 3 network protocol (Network Address Translation) information."
                      ::= { switchNwProtCfgModThree 1 }

           smNwProtInfoModThreeEntry  OBJECT-TYPE
                         SYNTAX SmNwProtInfoModThreeEntry
                         MAX-ACCESS  not-accessible
                         STATUS  current -- was mandatory
                         DESCRIPTION
                         "Switch module 3 network protocol (Network Address Translation) configuration 
                         information table entry"
                         INDEX { smNwProtInfoModThreeIndex }
                         ::= { smNwProtInfoModThreeTable 1 }

           SmNwProtInfoModThreeEntry ::= SEQUENCE {
                       smNwProtInfoModThreeIndex INTEGER,
                       smNwProtInfoModThreeId INTEGER,
                       smNwProtInfoModThreeExists INTEGER,
                       smNwProtInfoModThreePowerState INTEGER,
                       smNwProtInfoModThreeProtName OCTET STRING,
                       smNwProtInfoModThreeProtID INTEGER,
                       smNwProtInfoModThreeExtPort INTEGER,
                       smNwProtInfoModThreeIntPort INTEGER,
                       smNwProtInfoModThreeEnable INTEGER
                       }
           
           smNwProtInfoModThreeIndex OBJECT-TYPE
                       SYNTAX  Integer32 (0..2147483647) -- was INTEGER
                       MAX-ACCESS  read-only
                       STATUS  current -- was mandatory
                       DESCRIPTION
                       "Switch module 3 network protocol (Network Address Translation) information index."
                       ::= { smNwProtInfoModThreeEntry 1 }

           smNwProtInfoModThreeId OBJECT-TYPE
                       SYNTAX  INTEGER {
                         module1(1),
                         module2(2),
                         module3(3),
                         module4(4),
                         module5(5),
                         module6(6),
                         module7(7),
                         module8(8),
                         module9(9),
                         module10(10)
                       }
                       MAX-ACCESS  read-only
                       STATUS  current -- was mandatory
                       DESCRIPTION
                       "The switch module 3 numeric identifier."
                       ::= { smNwProtInfoModThreeEntry 2 }

           smNwProtInfoModThreeExists OBJECT-TYPE
                       SYNTAX  INTEGER {
                         false(0),
                         true(1)
                       }
                       MAX-ACCESS  read-only
                       STATUS  current -- was mandatory
                       DESCRIPTION
                       "Indicates whether the switch module 3 exists or not."
                       ::= { smNwProtInfoModThreeEntry 3 }

           smNwProtInfoModThreePowerState OBJECT-TYPE
                       SYNTAX  INTEGER {
                         off(0),
                         on(1)
                       }
                       MAX-ACCESS  read-only
                       STATUS  current -- was mandatory
                       DESCRIPTION
                       "Indicates whether the switch module 3 is powered on or not."
                       ::= { smNwProtInfoModThreeEntry 4 }

           smNwProtInfoModThreeProtName OBJECT-TYPE
                        SYNTAX  OCTET STRING
                        MAX-ACCESS  read-write
                        STATUS  current -- was mandatory
                        DESCRIPTION
                        "Protocol name"
                        ::= { smNwProtInfoModThreeEntry 5 }

           smNwProtInfoModThreeProtID OBJECT-TYPE
                        SYNTAX  INTEGER {
                          tcp(2), 
                          udp(3)
                        }  
                        MAX-ACCESS  read-write
                        STATUS  current -- was mandatory
                        DESCRIPTION
                        "Protocol ID"
                        ::= { smNwProtInfoModThreeEntry 6 }

           smNwProtInfoModThreeExtPort OBJECT-TYPE
                        SYNTAX  INTEGER
                        MAX-ACCESS  read-write
                        STATUS  current -- was mandatory
                        DESCRIPTION
                        "External port"
                        ::= { smNwProtInfoModThreeEntry 7 }

           smNwProtInfoModThreeIntPort OBJECT-TYPE
                        SYNTAX  INTEGER 
                        MAX-ACCESS  read-write
                        STATUS  current -- was mandatory
                        DESCRIPTION
                        "Internal port."
                        ::= { smNwProtInfoModThreeEntry 8 }

           smNwProtInfoModThreeEnable OBJECT-TYPE
                       SYNTAX  INTEGER {
                         disable(0),
                         enable(1)
                       }
                       MAX-ACCESS  read-write
                       STATUS  current -- was mandatory
                       DESCRIPTION
                       "Enable or disable the protocol entry."
                       ::= { smNwProtInfoModThreeEntry 9 }
           
           smNwProtInfoModThreeActivate OBJECT-TYPE
                       SYNTAX  INTEGER {
                         execute(1)
                       }
                       MAX-ACCESS  read-write
                       STATUS  current -- was mandatory
                       DESCRIPTION
                       "Activate all network protocol settings for the switch module.  
                       NOTE: Value returned for the GET command is meaningless for this MIB object." 
                       ::= { switchNwProtCfgModThree 2 }
           
           smNwProtInfoModThreeReset OBJECT-TYPE
                       SYNTAX  INTEGER {
                         execute(1)
                       }
                       MAX-ACCESS  read-write
                       STATUS  current -- was mandatory
                       DESCRIPTION
                       "Reset all network protocol settings for the switch module to default.  
                       NOTE: Value returned for the GET command is meaningless for this MIB object." 
                       ::= { switchNwProtCfgModThree 3 }


         switchNwProtCfgModFour  OBJECT IDENTIFIER ::= { switchNwProtCfg 4 }
         
          smNwProtInfoModFourTable OBJECT-TYPE
                      SYNTAX  SEQUENCE OF SmNwProtInfoModFourEntry
                      MAX-ACCESS  not-accessible
                      STATUS  current -- was mandatory
                      DESCRIPTION
                      "Switch module 4 network protocol (Network Address Translation) information."
                      ::= { switchNwProtCfgModFour 1 }

           smNwProtInfoModFourEntry  OBJECT-TYPE
                         SYNTAX SmNwProtInfoModFourEntry
                         MAX-ACCESS  not-accessible
                         STATUS  current -- was mandatory
                         DESCRIPTION
                         "Switch module 3 network protocol (Network Address Translation) configuration 
                         information table entry."
                         INDEX { smNwProtInfoModFourIndex }
                         ::= { smNwProtInfoModFourTable 1 }

           SmNwProtInfoModFourEntry ::= SEQUENCE {
                       smNwProtInfoModFourIndex INTEGER,
                       smNwProtInfoModFourId INTEGER,
                       smNwProtInfoModFourExists INTEGER,
                       smNwProtInfoModFourPowerState INTEGER,
                       smNwProtInfoModFourProtName OCTET STRING,
                       smNwProtInfoModFourProtID INTEGER,
                       smNwProtInfoModFourExtPort INTEGER,
                       smNwProtInfoModFourIntPort INTEGER,
                       smNwProtInfoModFourEnable INTEGER
                       }
           
           smNwProtInfoModFourIndex OBJECT-TYPE
                       SYNTAX  Integer32 (0..2147483647) -- was INTEGER
                       MAX-ACCESS  read-only
                       STATUS  current -- was mandatory
                       DESCRIPTION
                       "Switch module 4 network protocol (Network Address Translation) information index."
                       ::= { smNwProtInfoModFourEntry 1 }

           smNwProtInfoModFourId OBJECT-TYPE
                       SYNTAX  INTEGER {
                         module1(1),
                         module2(2),
                         module3(3),
                         module4(4),
                         module5(5),
                         module6(6),
                         module7(7),
                         module8(8),
                         module9(9),
                         module10(10)
                       }
                       MAX-ACCESS  read-only
                       STATUS  current -- was mandatory
                       DESCRIPTION
                       "The switch module 4 numeric identifier."
                       ::= { smNwProtInfoModFourEntry 2 }

           smNwProtInfoModFourExists OBJECT-TYPE
                       SYNTAX  INTEGER {
                         false(0),
                         true(1)
                       }
                       MAX-ACCESS  read-only
                       STATUS  current -- was mandatory
                       DESCRIPTION
                       "Indicates whether the switch module 4 exists or not."
                       ::= { smNwProtInfoModFourEntry 3 }

           smNwProtInfoModFourPowerState OBJECT-TYPE
                       SYNTAX  INTEGER {
                         off(0),
                         on(1)
                       }
                       MAX-ACCESS  read-only
                       STATUS  current -- was mandatory
                       DESCRIPTION
                       "Indicates whether the switch module 4 is powered on or not."
                       ::= { smNwProtInfoModFourEntry 4 }

           smNwProtInfoModFourProtName OBJECT-TYPE
                        SYNTAX  OCTET STRING
                        MAX-ACCESS  read-write
                        STATUS  current -- was mandatory
                        DESCRIPTION
                        "Protocol name"
                        ::= { smNwProtInfoModFourEntry 5 }

           smNwProtInfoModFourProtID OBJECT-TYPE
                        SYNTAX  INTEGER {
                          tcp(2), 
                          udp(3)
                        }  
                        MAX-ACCESS  read-write
                        STATUS  current -- was mandatory
                        DESCRIPTION
                        "Protocol ID"
                        ::= { smNwProtInfoModFourEntry 6 }

           smNwProtInfoModFourExtPort OBJECT-TYPE
                        SYNTAX  INTEGER
                        MAX-ACCESS  read-write
                        STATUS  current -- was mandatory
                        DESCRIPTION
                        "External port"
                        ::= { smNwProtInfoModFourEntry 7 }

           smNwProtInfoModFourIntPort OBJECT-TYPE
                        SYNTAX  INTEGER 
                        MAX-ACCESS  read-write
                        STATUS  current -- was mandatory
                        DESCRIPTION
                        "Internal port."
                        ::= { smNwProtInfoModFourEntry 8 }

           smNwProtInfoModFourEnable OBJECT-TYPE
                       SYNTAX  INTEGER {
                         disable(0),
                         enable(1)
                       }
                       MAX-ACCESS  read-write
                       STATUS  current -- was mandatory
                       DESCRIPTION
                       "Enable or disable the protocol entry."
                       ::= { smNwProtInfoModFourEntry 9 }
           
           smNwProtInfoModFourActivate OBJECT-TYPE
                       SYNTAX  INTEGER {
                         execute(1)
                       }
                       MAX-ACCESS  read-write
                       STATUS  current -- was mandatory
                       DESCRIPTION
                       "Activate all network protocol settings for the switch module.  
                       NOTE: Value returned for the GET command is meaningless for this MIB object." 
                       ::= { switchNwProtCfgModFour 2 }
           
           smNwProtInfoModFourReset OBJECT-TYPE
                       SYNTAX  INTEGER {
                         execute(1)
                       }
                       MAX-ACCESS  read-write
                       STATUS  current -- was mandatory
                       DESCRIPTION
                       "Reset all network protocol settings for the switch module to default.  
                       NOTE: Value returned for the GET command is meaningless for this MIB object." 
                       ::= { switchNwProtCfgModFour 3 }

         switchNwProtCfgModFive  OBJECT IDENTIFIER ::= { switchNwProtCfg 5 }
         
          smNwProtInfoModFiveTable OBJECT-TYPE
                      SYNTAX  SEQUENCE OF SmNwProtInfoModFiveEntry
                      MAX-ACCESS  not-accessible
                      STATUS  current -- was mandatory
                      DESCRIPTION
                      "Switch module 5 network protocol (Network Address Translation) information."
                      ::= { switchNwProtCfgModFive 1 }

           smNwProtInfoModFiveEntry  OBJECT-TYPE
                         SYNTAX SmNwProtInfoModFiveEntry
                         MAX-ACCESS  not-accessible
                         STATUS  current -- was mandatory
                         DESCRIPTION
                         "Switch module 5 network protocol (Network Address Translation) configuration 
                         information table entry"
                         INDEX { smNwProtInfoModFiveIndex }
                         ::= { smNwProtInfoModFiveTable 1 }

           SmNwProtInfoModFiveEntry ::= SEQUENCE {
                       smNwProtInfoModFiveIndex INTEGER,
                       smNwProtInfoModFiveId INTEGER,
                       smNwProtInfoModFiveExists INTEGER,
                       smNwProtInfoModFivePowerState INTEGER,
                       smNwProtInfoModFiveProtName OCTET STRING,
                       smNwProtInfoModFiveProtID INTEGER,
                       smNwProtInfoModFiveExtPort INTEGER,
                       smNwProtInfoModFiveIntPort INTEGER,
                       smNwProtInfoModFiveEnable INTEGER
                       }
           
           smNwProtInfoModFiveIndex OBJECT-TYPE
                       SYNTAX  Integer32 (0..2147483647) -- was INTEGER
                       MAX-ACCESS  read-only
                       STATUS  current -- was mandatory
                       DESCRIPTION
                       "Switch module 5 network protocol (Network Address Translation) information index."
                       ::= { smNwProtInfoModFiveEntry 1 }

           smNwProtInfoModFiveId OBJECT-TYPE
                       SYNTAX  INTEGER {
                         module1(1),
                         module2(2),
                         module3(3),
                         module4(4),
                         module5(5),
                         module6(6),
                         module7(7),
                         module8(8),
                         module9(9),
                         module10(10)
                       }
                       MAX-ACCESS  read-only
                       STATUS  current -- was mandatory
                       DESCRIPTION
                       "The switch module 5 numeric identifier."
                       ::= { smNwProtInfoModFiveEntry 2 }

           smNwProtInfoModFiveExists OBJECT-TYPE
                       SYNTAX  INTEGER {
                         false(0),
                         true(1)
                       }
                       MAX-ACCESS  read-only
                       STATUS  current -- was mandatory
                       DESCRIPTION
                       "Indicates whether the switch module 5 exists or not."
                       ::= { smNwProtInfoModFiveEntry 3 }

           smNwProtInfoModFivePowerState OBJECT-TYPE
                       SYNTAX  INTEGER {
                         off(0),
                         on(1)
                       }
                       MAX-ACCESS  read-only
                       STATUS  current -- was mandatory
                       DESCRIPTION
                       "Indicates whether the switch module 5 is powered on or not."
                       ::= { smNwProtInfoModFiveEntry 4 }

           smNwProtInfoModFiveProtName OBJECT-TYPE
                        SYNTAX  OCTET STRING
                        MAX-ACCESS  read-write
                        STATUS  current -- was mandatory
                        DESCRIPTION
                        "Protocol name"
                        ::= { smNwProtInfoModFiveEntry 5 }

           smNwProtInfoModFiveProtID OBJECT-TYPE
                        SYNTAX  INTEGER {
                          tcp(2), 
                          udp(3)
                        }  
                        MAX-ACCESS  read-write
                        STATUS  current -- was mandatory
                        DESCRIPTION
                        "Protocol ID"
                        ::= { smNwProtInfoModFiveEntry 6 }

           smNwProtInfoModFiveExtPort OBJECT-TYPE
                        SYNTAX  INTEGER
                        MAX-ACCESS  read-write
                        STATUS  current -- was mandatory
                        DESCRIPTION
                        "External port"
                        ::= { smNwProtInfoModFiveEntry 7 }

           smNwProtInfoModFiveIntPort OBJECT-TYPE
                        SYNTAX  INTEGER 
                        MAX-ACCESS  read-write
                        STATUS  current -- was mandatory
                        DESCRIPTION
                        "Internal port."
                        ::= { smNwProtInfoModFiveEntry 8 }

           smNwProtInfoModFiveEnable OBJECT-TYPE
                       SYNTAX  INTEGER {
                         disable(0),
                         enable(1)
                       }
                       MAX-ACCESS  read-write
                       STATUS  current -- was mandatory
                       DESCRIPTION
                       "Enable or disable the protocol entry."
                       ::= { smNwProtInfoModFiveEntry 9 }

           smNwProtInfoModFiveActivate OBJECT-TYPE
                       SYNTAX  INTEGER {
                         execute(1)
                       }
                       MAX-ACCESS  read-write
                       STATUS  current -- was mandatory
                       DESCRIPTION
                       "Activate all network protocol settings for the switch module.  
                       NOTE: Value returned for the GET command is meaningless for this MIB object." 
                       ::= { switchNwProtCfgModFive 2 }
           
           smNwProtInfoModFiveReset OBJECT-TYPE
                       SYNTAX  INTEGER {
                         execute(1)
                       }
                       MAX-ACCESS  read-write
                       STATUS  current -- was mandatory
                       DESCRIPTION
                       "Reset all network protocol settings for the switch module to default.  
                       NOTE: Value returned for the GET command is meaningless for this MIB object." 
                       ::= { switchNwProtCfgModFive 3 }
         
         
         switchNwProtCfgModSix  OBJECT IDENTIFIER ::= { switchNwProtCfg 6 }
         
          smNwProtInfoModSixTable OBJECT-TYPE
                      SYNTAX  SEQUENCE OF SmNwProtInfoModSixEntry
                      MAX-ACCESS  not-accessible
                      STATUS  current -- was mandatory
                      DESCRIPTION
                      "Switch module 6 network protocol (Network Address Translation) information."
                      ::= { switchNwProtCfgModSix 1 }

           smNwProtInfoModSixEntry  OBJECT-TYPE
                         SYNTAX SmNwProtInfoModSixEntry
                         MAX-ACCESS  not-accessible
                         STATUS  current -- was mandatory
                         DESCRIPTION
                         "Switch module 6 network protocol (Network Address Translation) configuration 
                         information table entry"
                         INDEX { smNwProtInfoModSixIndex }
                         ::= { smNwProtInfoModSixTable 1 }

           SmNwProtInfoModSixEntry ::= SEQUENCE {
                       smNwProtInfoModSixIndex INTEGER,
                       smNwProtInfoModSixId INTEGER,
                       smNwProtInfoModSixExists INTEGER,
                       smNwProtInfoModSixPowerState INTEGER,
                       smNwProtInfoModSixProtName OCTET STRING,
                       smNwProtInfoModSixProtID INTEGER,
                       smNwProtInfoModSixExtPort INTEGER,
                       smNwProtInfoModSixIntPort INTEGER,
                       smNwProtInfoModSixEnable INTEGER
                       }
           
           smNwProtInfoModSixIndex OBJECT-TYPE
                       SYNTAX  Integer32 (0..2147483647) -- was INTEGER
                       MAX-ACCESS  read-only
                       STATUS  current -- was mandatory
                       DESCRIPTION
                       "Switch module 6 network protocol (Network Address Translation) information index."
                       ::= { smNwProtInfoModSixEntry 1 }

           smNwProtInfoModSixId OBJECT-TYPE
                       SYNTAX  INTEGER {
                         module1(1),
                         module2(2),
                         module3(3),
                         module4(4),
                         module5(5),
                         module6(6),
                         module7(7),
                         module8(8),
                         module9(9),
                         module10(10)
                       }
                       MAX-ACCESS  read-only
                       STATUS  current -- was mandatory
                       DESCRIPTION
                       "The switch module 6 numeric identifier."
                       ::= { smNwProtInfoModSixEntry 2 }

           smNwProtInfoModSixExists OBJECT-TYPE
                       SYNTAX  INTEGER {
                         false(0),
                         true(1)
                       }
                       MAX-ACCESS  read-only
                       STATUS  current -- was mandatory
                       DESCRIPTION
                       "Indicates whether the switch module 6 exists or not."
                       ::= { smNwProtInfoModSixEntry 3 }

           smNwProtInfoModSixPowerState OBJECT-TYPE
                       SYNTAX  INTEGER {
                         off(0),
                         on(1)
                       }
                       MAX-ACCESS  read-only
                       STATUS  current -- was mandatory
                       DESCRIPTION
                       "Indicates whether the switch module 6 is powered on or not."
                       ::= { smNwProtInfoModSixEntry 4 }

           smNwProtInfoModSixProtName OBJECT-TYPE
                        SYNTAX  OCTET STRING
                        MAX-ACCESS  read-write
                        STATUS  current -- was mandatory
                        DESCRIPTION
                        "Protocol name"
                        ::= { smNwProtInfoModSixEntry 5 }

           smNwProtInfoModSixProtID OBJECT-TYPE
                        SYNTAX  INTEGER {
                          tcp(2), 
                          udp(3)
                        }  
                        MAX-ACCESS  read-write
                        STATUS  current -- was mandatory
                        DESCRIPTION
                        "Protocol ID"
                        ::= { smNwProtInfoModSixEntry 6 }

           smNwProtInfoModSixExtPort OBJECT-TYPE
                        SYNTAX  INTEGER
                        MAX-ACCESS  read-write
                        STATUS  current -- was mandatory
                        DESCRIPTION
                        "External port"
                        ::= { smNwProtInfoModSixEntry 7 }

           smNwProtInfoModSixIntPort OBJECT-TYPE
                        SYNTAX  INTEGER 
                        MAX-ACCESS  read-write
                        STATUS  current -- was mandatory
                        DESCRIPTION
                        "Internal port."
                        ::= { smNwProtInfoModSixEntry 8 }

           smNwProtInfoModSixEnable OBJECT-TYPE
                       SYNTAX  INTEGER {
                         disable(0),
                         enable(1)
                       }
                       MAX-ACCESS  read-write
                       STATUS  current -- was mandatory
                       DESCRIPTION
                       "Enable or disable the protocol entry."
                       ::= { smNwProtInfoModSixEntry 9 }
           
           smNwProtInfoModSixActivate OBJECT-TYPE
                       SYNTAX  INTEGER {
                         execute(1)
                       }
                       MAX-ACCESS  read-write
                       STATUS  current -- was mandatory
                       DESCRIPTION
                       "Activate all network protocol settings for the switch module.  
                       NOTE: Value returned for the GET command is meaningless for this MIB object." 
                       ::= { switchNwProtCfgModSix 2 }
           
           smNwProtInfoModSixReset OBJECT-TYPE
                       SYNTAX  INTEGER {
                         execute(1)
                       }
                       MAX-ACCESS  read-write
                       STATUS  current -- was mandatory
                       DESCRIPTION
                       "Reset all network protocol settings for the switch module to default.  
                       NOTE: Value returned for the GET command is meaningless for this MIB object." 
                       ::= { switchNwProtCfgModSix 3 }


          switchNwProtCfgModSeven  OBJECT IDENTIFIER ::= { switchNwProtCfg 7 }
          
          smNwProtInfoModSevenTable OBJECT-TYPE
                      SYNTAX  SEQUENCE OF SmNwProtInfoModSevenEntry
                      MAX-ACCESS  not-accessible
                      STATUS  current -- was mandatory
                      DESCRIPTION
                      "Switch module 7 network protocol (Network Address Translation) information."
                      ::= { switchNwProtCfgModSeven 1 }

           smNwProtInfoModSevenEntry  OBJECT-TYPE
                         SYNTAX SmNwProtInfoModSevenEntry
                         MAX-ACCESS  not-accessible
                         STATUS  current -- was mandatory
                         DESCRIPTION
                         "Switch module 7 network protocol (Network Address Translation) configuration 
                         information table entry"
                         INDEX { smNwProtInfoModSevenIndex }
                         ::= { smNwProtInfoModSevenTable 1 }

           SmNwProtInfoModSevenEntry ::= SEQUENCE {
                       smNwProtInfoModSevenIndex INTEGER,
                       smNwProtInfoModSevenId INTEGER,
                       smNwProtInfoModSevenExists INTEGER,
                       smNwProtInfoModSevenPowerState INTEGER,
                       smNwProtInfoModSevenProtName OCTET STRING,
                       smNwProtInfoModSevenProtID INTEGER,
                       smNwProtInfoModSevenExtPort INTEGER,
                       smNwProtInfoModSevenIntPort INTEGER,
                       smNwProtInfoModSevenEnable INTEGER
                       }
           
           smNwProtInfoModSevenIndex OBJECT-TYPE
                       SYNTAX  Integer32 (0..2147483647) -- was INTEGER
                       MAX-ACCESS  read-only
                       STATUS  current -- was mandatory
                       DESCRIPTION
                       "Switch module 7 network protocol (Network Address Translation) information index."
                       ::= { smNwProtInfoModSevenEntry 1 }

           smNwProtInfoModSevenId OBJECT-TYPE
                       SYNTAX  INTEGER {
                         module1(1),
                         module2(2),
                         module3(3),
                         module4(4),
                         module5(5),
                         module6(6),
                         module7(7),
                         module8(8),
                         module9(9),
                         module10(10)
                       }
                       MAX-ACCESS  read-only
                       STATUS  current -- was mandatory
                       DESCRIPTION
                       "The switch module 7 numeric identifier."
                       ::= { smNwProtInfoModSevenEntry 2 }

           smNwProtInfoModSevenExists OBJECT-TYPE
                       SYNTAX  INTEGER {
                         false(0),
                         true(1)
                       }
                       MAX-ACCESS  read-only
                       STATUS  current -- was mandatory
                       DESCRIPTION
                       "Indicates whether the switch module 7 exists or not."
                       ::= { smNwProtInfoModSevenEntry 3 }

           smNwProtInfoModSevenPowerState OBJECT-TYPE
                       SYNTAX  INTEGER {
                         off(0),
                         on(1)
                       }
                       MAX-ACCESS  read-only
                       STATUS  current -- was mandatory
                       DESCRIPTION
                       "Indicates whether the switch module 7 is powered on or not."
                       ::= { smNwProtInfoModSevenEntry 4 }

           smNwProtInfoModSevenProtName OBJECT-TYPE
                        SYNTAX  OCTET STRING
                        MAX-ACCESS  read-write
                        STATUS  current -- was mandatory
                        DESCRIPTION
                        "Protocol name"
                        ::= { smNwProtInfoModSevenEntry 5 }

           smNwProtInfoModSevenProtID OBJECT-TYPE
                        SYNTAX  INTEGER {
                          tcp(2), 
                          udp(3)
                        }  
                        MAX-ACCESS  read-write
                        STATUS  current -- was mandatory
                        DESCRIPTION
                        "Protocol ID"
                        ::= { smNwProtInfoModSevenEntry 6 }

           smNwProtInfoModSevenExtPort OBJECT-TYPE
                        SYNTAX  INTEGER
                        MAX-ACCESS  read-write
                        STATUS  current -- was mandatory
                        DESCRIPTION
                        "External port"
                        ::= { smNwProtInfoModSevenEntry 7 }

           smNwProtInfoModSevenIntPort OBJECT-TYPE
                        SYNTAX  INTEGER 
                        MAX-ACCESS  read-write
                        STATUS  current -- was mandatory
                        DESCRIPTION
                        "Internal port."
                        ::= { smNwProtInfoModSevenEntry 8 }

           smNwProtInfoModSevenEnable OBJECT-TYPE
                       SYNTAX  INTEGER {
                         disable(0),
                         enable(1)
                       }
                       MAX-ACCESS  read-write
                       STATUS  current -- was mandatory
                       DESCRIPTION
                       "Enable or disable the protocol entry."
                       ::= { smNwProtInfoModSevenEntry 9 }
           
           smNwProtInfoModSevenActivate OBJECT-TYPE
                       SYNTAX  INTEGER {
                         execute(1)
                       }
                       MAX-ACCESS  read-write
                       STATUS  current -- was mandatory
                       DESCRIPTION
                       "Activate all network protocol settings for the switch module.  
                       NOTE: Value returned for the GET command is meaningless for this MIB object." 
                       ::= { switchNwProtCfgModSeven 2 }
           
           smNwProtInfoModSevenReset OBJECT-TYPE
                       SYNTAX  INTEGER {
                         execute(1)
                       }
                       MAX-ACCESS  read-write
                       STATUS  current -- was mandatory
                       DESCRIPTION
                       "Reset all network protocol settings for the switch module to default.  
                       NOTE: Value returned for the GET command is meaningless for this MIB object." 
                       ::= { switchNwProtCfgModSeven 3 }


          switchNwProtCfgModEight  OBJECT IDENTIFIER ::= { switchNwProtCfg 8 }
          
          smNwProtInfoModEightTable OBJECT-TYPE
                      SYNTAX  SEQUENCE OF SmNwProtInfoModEightEntry
                      MAX-ACCESS  not-accessible
                      STATUS  current -- was mandatory
                      DESCRIPTION
                      "Switch module 8 network protocol (Network Address Translation) information."
                      ::= { switchNwProtCfgModEight 1 }

           smNwProtInfoModEightEntry  OBJECT-TYPE
                         SYNTAX SmNwProtInfoModEightEntry
                         MAX-ACCESS  not-accessible
                         STATUS  current -- was mandatory
                         DESCRIPTION
                         "Switch module 8 network protocol (Network Address Translation) configuration 
                         information table entry"
                         INDEX { smNwProtInfoModEightIndex }
                         ::= { smNwProtInfoModEightTable 1 }

           SmNwProtInfoModEightEntry ::= SEQUENCE {
                       smNwProtInfoModEightIndex INTEGER,
                       smNwProtInfoModEightId INTEGER,
                       smNwProtInfoModEightExists INTEGER,
                       smNwProtInfoModEightPowerState INTEGER,
                       smNwProtInfoModEightProtName OCTET STRING,
                       smNwProtInfoModEightProtID INTEGER,
                       smNwProtInfoModEightExtPort INTEGER,
                       smNwProtInfoModEightIntPort INTEGER,
                       smNwProtInfoModEightEnable INTEGER
                       }
           
           smNwProtInfoModEightIndex OBJECT-TYPE
                       SYNTAX  Integer32 (0..2147483647) -- was INTEGER
                       MAX-ACCESS  read-only
                       STATUS  current -- was mandatory
                       DESCRIPTION
                       "Switch module 8 network protocol (Network Address Translation) information index."
                       ::= { smNwProtInfoModEightEntry 1 }

           smNwProtInfoModEightId OBJECT-TYPE
                       SYNTAX  INTEGER {
                         module1(1),
                         module2(2),
                         module3(3),
                         module4(4),
                         module5(5),
                         module6(6),
                         module7(7),
                         module8(8),
                         module9(9),
                         module10(10)
                       }
                       MAX-ACCESS  read-only
                       STATUS  current -- was mandatory
                       DESCRIPTION
                       "The switch module 8 numeric identifier."
                       ::= { smNwProtInfoModEightEntry 2 }

           smNwProtInfoModEightExists OBJECT-TYPE
                       SYNTAX  INTEGER {
                         false(0),
                         true(1)
                       }
                       MAX-ACCESS  read-only
                       STATUS  current -- was mandatory
                       DESCRIPTION
                       "Indicates whether the switch module 8 exists or not."
                       ::= { smNwProtInfoModEightEntry 3 }

           smNwProtInfoModEightPowerState OBJECT-TYPE
                       SYNTAX  INTEGER {
                         off(0),
                         on(1)
                       }
                       MAX-ACCESS  read-only
                       STATUS  current -- was mandatory
                       DESCRIPTION
                       "Indicates whether the switch module 8 is powered on or not."
                       ::= { smNwProtInfoModEightEntry 4 }

           smNwProtInfoModEightProtName OBJECT-TYPE
                        SYNTAX  OCTET STRING
                        MAX-ACCESS  read-write
                        STATUS  current -- was mandatory
                        DESCRIPTION
                        "Protocol name"
                        ::= { smNwProtInfoModEightEntry 5 }

           smNwProtInfoModEightProtID OBJECT-TYPE
                        SYNTAX  INTEGER {
                          tcp(2), 
                          udp(3)
                        }  
                        MAX-ACCESS  read-write
                        STATUS  current -- was mandatory
                        DESCRIPTION
                        "Protocol ID"
                        ::= { smNwProtInfoModEightEntry 6 }

           smNwProtInfoModEightExtPort OBJECT-TYPE
                        SYNTAX  INTEGER
                        MAX-ACCESS  read-write
                        STATUS  current -- was mandatory
                        DESCRIPTION
                        "External port"
                        ::= { smNwProtInfoModEightEntry 7 }

           smNwProtInfoModEightIntPort OBJECT-TYPE
                        SYNTAX  INTEGER 
                        MAX-ACCESS  read-write
                        STATUS  current -- was mandatory
                        DESCRIPTION
                        "Internal port."
                        ::= { smNwProtInfoModEightEntry 8 }

           smNwProtInfoModEightEnable OBJECT-TYPE
                       SYNTAX  INTEGER {
                         disable(0),
                         enable(1)
                       }
                       MAX-ACCESS  read-write
                       STATUS  current -- was mandatory
                       DESCRIPTION
                       "Enable or disable the protocol entry."
                       ::= { smNwProtInfoModEightEntry 9 }
           
           smNwProtInfoModEightActivate OBJECT-TYPE
                       SYNTAX  INTEGER {
                         execute(1)
                       }
                       MAX-ACCESS  read-write
                       STATUS  current -- was mandatory
                       DESCRIPTION
                       "Activate all network protocol settings for the switch module.  
                       NOTE: Value returned for the GET command is meaningless for this MIB object." 
                       ::= { switchNwProtCfgModEight 2 }
           
           smNwProtInfoModEightReset OBJECT-TYPE
                       SYNTAX  INTEGER {
                         execute(1)
                       }
                       MAX-ACCESS  read-write
                       STATUS  current -- was mandatory
                       DESCRIPTION
                       "Reset all network protocol settings for the switch module to default.  
                       NOTE: Value returned for the GET command is meaningless for this MIB object." 
                       ::= { switchNwProtCfgModEight 3 }

          switchNwProtCfgModNine  OBJECT IDENTIFIER ::= { switchNwProtCfg 9 }
          
          smNwProtInfoModNineTable OBJECT-TYPE
                      SYNTAX  SEQUENCE OF SmNwProtInfoModNineEntry
                      MAX-ACCESS  not-accessible
                      STATUS  current -- was mandatory
                      DESCRIPTION
                      "Switch module 9 network protocol (Network Address Translation) information."
                      ::= { switchNwProtCfgModNine 1 }

           smNwProtInfoModNineEntry  OBJECT-TYPE
                         SYNTAX SmNwProtInfoModNineEntry
                         MAX-ACCESS  not-accessible
                         STATUS  current -- was mandatory
                         DESCRIPTION
                         "Switch module 9 network protocol (Network Address Translation) configuration 
                         information table entry"
                         INDEX { smNwProtInfoModNineIndex }
                         ::= { smNwProtInfoModNineTable 1 }

           SmNwProtInfoModNineEntry ::= SEQUENCE {
                       smNwProtInfoModNineIndex INTEGER,
                       smNwProtInfoModNineId INTEGER,
                       smNwProtInfoModNineExists INTEGER,
                       smNwProtInfoModNinePowerState INTEGER,
                       smNwProtInfoModNineProtName OCTET STRING,
                       smNwProtInfoModNineProtID INTEGER,
                       smNwProtInfoModNineExtPort INTEGER,
                       smNwProtInfoModNineIntPort INTEGER,
                       smNwProtInfoModNineEnable INTEGER
                       }
           
           smNwProtInfoModNineIndex OBJECT-TYPE
                       SYNTAX  Integer32 (0..2147483647) -- was INTEGER
                       MAX-ACCESS  read-only
                       STATUS  current -- was mandatory
                       DESCRIPTION
                       "Switch module 9 network protocol (Network Address Translation) information index."
                       ::= { smNwProtInfoModNineEntry 1 }

           smNwProtInfoModNineId OBJECT-TYPE
                       SYNTAX  INTEGER {
                         module1(1),
                         module2(2),
                         module3(3),
                         module4(4),
                         module5(5),
                         module6(6),
                         module7(7),
                         module8(8),
                         module9(9),
                         module10(10)
                       }
                       MAX-ACCESS  read-only
                       STATUS  current -- was mandatory
                       DESCRIPTION
                       "The switch module 9 numeric identifier."
                       ::= { smNwProtInfoModNineEntry 2 }

           smNwProtInfoModNineExists OBJECT-TYPE
                       SYNTAX  INTEGER {
                         false(0),
                         true(1)
                       }
                       MAX-ACCESS  read-only
                       STATUS  current -- was mandatory
                       DESCRIPTION
                       "Indicates whether the switch module 9 exists or not."
                       ::= { smNwProtInfoModNineEntry 3 }

           smNwProtInfoModNinePowerState OBJECT-TYPE
                       SYNTAX  INTEGER {
                         off(0),
                         on(1)
                       }
                       MAX-ACCESS  read-only
                       STATUS  current -- was mandatory
                       DESCRIPTION
                       "Indicates whether the switch module 9 is powered on or not."
                       ::= { smNwProtInfoModNineEntry 4 }

           smNwProtInfoModNineProtName OBJECT-TYPE
                        SYNTAX  OCTET STRING
                        MAX-ACCESS  read-write
                        STATUS  current -- was mandatory
                        DESCRIPTION
                        "Protocol name"
                        ::= { smNwProtInfoModNineEntry 5 }

           smNwProtInfoModNineProtID OBJECT-TYPE
                        SYNTAX  INTEGER {
                          tcp(2), 
                          udp(3)
                        }  
                        MAX-ACCESS  read-write
                        STATUS  current -- was mandatory
                        DESCRIPTION
                        "Protocol ID"
                        ::= { smNwProtInfoModNineEntry 6 }

           smNwProtInfoModNineExtPort OBJECT-TYPE
                        SYNTAX  INTEGER
                        MAX-ACCESS  read-write
                        STATUS  current -- was mandatory
                        DESCRIPTION
                        "External port"
                        ::= { smNwProtInfoModNineEntry 7 }

           smNwProtInfoModNineIntPort OBJECT-TYPE
                        SYNTAX  INTEGER 
                        MAX-ACCESS  read-write
                        STATUS  current -- was mandatory
                        DESCRIPTION
                        "Internal port."
                        ::= { smNwProtInfoModNineEntry 8 }

           smNwProtInfoModNineEnable OBJECT-TYPE
                       SYNTAX  INTEGER {
                         disable(0),
                         enable(1)
                       }
                       MAX-ACCESS  read-write
                       STATUS  current -- was mandatory
                       DESCRIPTION
                       "Enable or disable the protocol entry."
                       ::= { smNwProtInfoModNineEntry 9 }
           
           smNwProtInfoModNineActivate OBJECT-TYPE
                       SYNTAX  INTEGER {
                         execute(1)
                       }
                       MAX-ACCESS  read-write
                       STATUS  current -- was mandatory
                       DESCRIPTION
                       "Activate all network protocol settings for the switch module.  
                       NOTE: Value returned for the GET command is meaningless for this MIB object." 
                       ::= { switchNwProtCfgModNine 2 }
           
           smNwProtInfoModNineReset OBJECT-TYPE
                       SYNTAX  INTEGER {
                         execute(1)
                       }
                       MAX-ACCESS  read-write
                       STATUS  current -- was mandatory
                       DESCRIPTION
                       "Reset all network protocol settings for the switch module to default.  
                       NOTE: Value returned for the GET command is meaningless for this MIB object." 
                       ::= { switchNwProtCfgModNine 3 }

          switchNwProtCfgModTen  OBJECT IDENTIFIER ::= { switchNwProtCfg 10 }
          
          smNwProtInfoModTenTable OBJECT-TYPE
                      SYNTAX  SEQUENCE OF SmNwProtInfoModTenEntry
                      MAX-ACCESS  not-accessible
                      STATUS  current -- was mandatory
                      DESCRIPTION
                      "Switch module 10 network protocol (Network Address Translation) information."
                      ::= { switchNwProtCfgModTen 1 }

           smNwProtInfoModTenEntry  OBJECT-TYPE
                         SYNTAX SmNwProtInfoModTenEntry
                         MAX-ACCESS  not-accessible
                         STATUS  current -- was mandatory
                         DESCRIPTION
                         "Switch module 10 network protocol (Network Address Translation) configuration 
                         information table entry"
                         INDEX { smNwProtInfoModTenIndex }
                         ::= { smNwProtInfoModTenTable 1 }

           SmNwProtInfoModTenEntry ::= SEQUENCE {
                       smNwProtInfoModTenIndex INTEGER,
                       smNwProtInfoModTenId INTEGER,
                       smNwProtInfoModTenExists INTEGER,
                       smNwProtInfoModTenPowerState INTEGER,
                       smNwProtInfoModTenProtName OCTET STRING,
                       smNwProtInfoModTenProtID INTEGER,
                       smNwProtInfoModTenExtPort INTEGER,
                       smNwProtInfoModTenIntPort INTEGER,
                       smNwProtInfoModTenEnable INTEGER
                       }
           
           smNwProtInfoModTenIndex OBJECT-TYPE
                       SYNTAX  Integer32 (0..2147483647) -- was INTEGER
                       MAX-ACCESS  read-only
                       STATUS  current -- was mandatory
                       DESCRIPTION
                       "Switch module 10 network protocol (Network Address Translation) information index."
                       ::= { smNwProtInfoModTenEntry 1 }

           smNwProtInfoModTenId OBJECT-TYPE
                       SYNTAX  INTEGER {
                         module1(1),
                         module2(2),
                         module3(3),
                         module4(4),
                         module5(5),
                         module6(6),
                         module7(7),
                         module8(8),
                         module9(9),
                         module10(10)
                       }
                       MAX-ACCESS  read-only
                       STATUS  current -- was mandatory
                       DESCRIPTION
                       "The switch module 10 numeric identifier."
                       ::= { smNwProtInfoModTenEntry 2 }

           smNwProtInfoModTenExists OBJECT-TYPE
                       SYNTAX  INTEGER {
                         false(0),
                         true(1)
                       }
                       MAX-ACCESS  read-only
                       STATUS  current -- was mandatory
                       DESCRIPTION
                       "Indicates whether the switch module 10 exists or not."
                       ::= { smNwProtInfoModTenEntry 3 }

           smNwProtInfoModTenPowerState OBJECT-TYPE
                       SYNTAX  INTEGER {
                         off(0),
                         on(1)
                       }
                       MAX-ACCESS  read-only
                       STATUS  current -- was mandatory
                       DESCRIPTION
                       "Indicates whether the switch module 10 is powered on or not."
                       ::= { smNwProtInfoModTenEntry 4 }

           smNwProtInfoModTenProtName OBJECT-TYPE
                        SYNTAX  OCTET STRING
                        MAX-ACCESS  read-write
                        STATUS  current -- was mandatory
                        DESCRIPTION
                        "Protocol name"
                        ::= { smNwProtInfoModTenEntry 5 }

           smNwProtInfoModTenProtID OBJECT-TYPE
                        SYNTAX  INTEGER {
                          tcp(2), 
                          udp(3)
                        }  
                        MAX-ACCESS  read-write
                        STATUS  current -- was mandatory
                        DESCRIPTION
                        "Protocol ID"
                        ::= { smNwProtInfoModTenEntry 6 }

           smNwProtInfoModTenExtPort OBJECT-TYPE
                        SYNTAX  INTEGER
                        MAX-ACCESS  read-write
                        STATUS  current -- was mandatory
                        DESCRIPTION
                        "External port"
                        ::= { smNwProtInfoModTenEntry 7 }

           smNwProtInfoModTenIntPort OBJECT-TYPE
                        SYNTAX  INTEGER 
                        MAX-ACCESS  read-write
                        STATUS  current -- was mandatory
                        DESCRIPTION
                        "Internal port."
                        ::= { smNwProtInfoModTenEntry 8 }

           smNwProtInfoModTenEnable OBJECT-TYPE
                       SYNTAX  INTEGER {
                         disable(0),
                         enable(1)
                       }
                       MAX-ACCESS  read-write
                       STATUS  current -- was mandatory
                       DESCRIPTION
                       "Enable or disable the protocol entry."
                       ::= { smNwProtInfoModTenEntry 9 }
                       
           smNwProtInfoModTenActivate OBJECT-TYPE
                       SYNTAX  INTEGER {
                         execute(1)
                       }
                       MAX-ACCESS  read-write
                       STATUS  current -- was mandatory
                       DESCRIPTION
                       "Activate all network protocol settings for the switch module.  
                       NOTE: Value returned for the GET command is meaningless for this MIB object." 
                       ::= { switchNwProtCfgModTen 2 }
           
           smNwProtInfoModTenReset OBJECT-TYPE
                       SYNTAX  INTEGER {
                         execute(1)
                       }
                       MAX-ACCESS  read-write
                       STATUS  current -- was mandatory
                       DESCRIPTION
                       "Reset all network protocol settings for the switch module to default.  
                       NOTE: Value returned for the GET command is meaningless for this MIB object." 
                       ::= { switchNwProtCfgModTen 3 }

         -- ********************************************************************************
         -- Switch module port tables
         -- ********************************************************************************
         switchPortCfg OBJECT IDENTIFIER ::= { switchModuleConfig 2 }
         
         switchModOnePortCfg  OBJECT IDENTIFIER ::= { switchPortCfg 1 }
         
          smOnePortCfgTable OBJECT-TYPE
                      SYNTAX  SEQUENCE OF SmOnePortCfgEntry
                      MAX-ACCESS  not-accessible
                      STATUS  current -- was mandatory
                      DESCRIPTION
                      "Switch Module 1 port configuration information.
                      NOTE: This option is not supported on all I/O modules."
                      ::= { switchModOnePortCfg 1 }

           smOnePortCfgEntry  OBJECT-TYPE
                         SYNTAX SmOnePortCfgEntry
                         MAX-ACCESS  not-accessible
                         STATUS  current -- was mandatory
                         DESCRIPTION
                         "Switch Module 1 port configuration information table entry"
                         INDEX { smOnePortCfgIndex }
                         ::= { smOnePortCfgTable 1 }

           SmOnePortCfgEntry ::= SEQUENCE {
                       smOnePortCfgIndex INTEGER,
                       smOnePortCfgLabel OCTET STRING,
                       smOnePortCfgType INTEGER,
                       smOnePortCfgLinkSetting INTEGER,
                       smOnePortCfgLinkState INTEGER,
                       smOnePortCfgSpeedSetting OCTET STRING,
                       smOnePortCfgSpeedStatus OCTET STRING,
                       smOnePortCfgAvailSpeeds OCTET STRING
                       }
           
           smOnePortCfgIndex OBJECT-TYPE
                       SYNTAX  Integer32 (0..2147483647) -- was INTEGER
                       MAX-ACCESS  read-only
                       STATUS  current -- was mandatory
                       DESCRIPTION
                       "Switch Module 1 port sequence index."
                       ::= { smOnePortCfgEntry 1 }

           smOnePortCfgLabel OBJECT-TYPE
                        SYNTAX  OCTET STRING
                        MAX-ACCESS  read-only
                        STATUS  current -- was mandatory
                        DESCRIPTION
                        "Switch Module 1 port label"
                        ::= { smOnePortCfgEntry 2 }

           smOnePortCfgType OBJECT-TYPE
                        SYNTAX  INTEGER {
                          unused(0),
                          externalPort(1), 
                          externalManagementPort(2),
                          externalDualPort(3),
                          bladePort(4),
                          mmManagementPort(5),
                          uplinkPort(6),
                          interModulePort(7),
                          interModuleManagementPort(8),
                          interModuleDualPort(9)
                        }
                        MAX-ACCESS  read-only
                        STATUS  current -- was mandatory
                        DESCRIPTION
                        "Switch Module 1 port type:
                        External port: This port is connected to external device and is for data traffic.
                        External management port: This port is solely for external management connection. 
                                This port is not used for data traffic from remote to blades.
                        External dual port: This external port is used for both data traffic to blades as well as for management.
                        Blade port: This port is connected to the blade.
                        Management Module Management port: This port is connected to the Management Module.
                        Uplink port: This port is configured for up link functionality.
                        Inter-Module port: This port is either by design connected to another I/O Module, 
                                by user configured, or by AMM setting the port type.
                        Inter-Module Management port: This port is connected to another I/O Module for management purpose.
                                The port type is either by design connected to another I/O Module, by user configured, 
                                or by AMM setting the port type.
                        Inter-Module Dual port:  The port is connected to another I/O Module and can be used for both data 
                                and management purposes. The port type is either by design connected to another I/O Module, 
                                by user configured, or by AMM setting the port type."
                        ::= { smOnePortCfgEntry 3 }

           smOnePortCfgLinkSetting OBJECT-TYPE
                        SYNTAX  INTEGER {
                          down(0),
                          up(1)
                        }
                        MAX-ACCESS  read-write
                        STATUS  current -- was mandatory
                        DESCRIPTION
                        "Current port link setting for Switch Module 1."
                        ::= { smOnePortCfgEntry 4 }
                        
           smOnePortCfgLinkState OBJECT-TYPE
                        SYNTAX  INTEGER {
                          down(0),
                          up(1)
                        }
                        MAX-ACCESS  read-only
                        STATUS  current -- was mandatory
                        DESCRIPTION
                        "Current port link state of Switch Module 1."
                        ::= { smOnePortCfgEntry 5 }
                                     
           smOnePortCfgSpeedSetting OBJECT-TYPE
                        SYNTAX  OCTET STRING
                        MAX-ACCESS  read-write
                        STATUS  current -- was mandatory
                        DESCRIPTION
                        "Set the port speed using the data rate and duplex value. For examples:
                        100mf: 100 Mbps in Half Duplex;
                        10gf: 10 Gbps in Full Duplex;
                        auto: The working speed of the physical port can be tuned automatically.

                        NOTE: Only the speeds from smOnePortCfgAvailSpeeds object are applicable to setting
                        this mib object."
                        ::= { smOnePortCfgEntry 6 }

           smOnePortCfgSpeedStatus OBJECT-TYPE
                        SYNTAX  OCTET STRING
                        MAX-ACCESS  read-only
                        STATUS  current -- was mandatory
                        DESCRIPTION
                        "Current port speed of Switch Module 1."
                        ::= { smOnePortCfgEntry 7 }
                        
           smOnePortCfgAvailSpeeds OBJECT-TYPE
                        SYNTAX  OCTET STRING 
                        MAX-ACCESS  read-only
                        STATUS  current -- was mandatory
                        DESCRIPTION
                        "Available speed setting per port for Switch Module 1.
                        If there is more than one setting, the speeds are separated by a comma and then a space."
                        ::= { smOnePortCfgEntry 8 }

         switchModTwoPortCfg  OBJECT IDENTIFIER ::= { switchPortCfg 2 }
         
          smTwoPortCfgTable OBJECT-TYPE
                      SYNTAX  SEQUENCE OF SmTwoPortCfgEntry
                      MAX-ACCESS  not-accessible
                      STATUS  current -- was mandatory
                      DESCRIPTION
                      "Switch Module 2 port configuration information.
                      Note:  This option is not supported on all I/O modules."
                      ::= { switchModTwoPortCfg 1 }

           smTwoPortCfgEntry  OBJECT-TYPE
                         SYNTAX SmTwoPortCfgEntry
                         MAX-ACCESS  not-accessible
                         STATUS  current -- was mandatory
                         DESCRIPTION
                         "Switch Module 2 port configuration information table entry"
                         INDEX { smTwoPortCfgIndex }
                         ::= { smTwoPortCfgTable 1 }

           SmTwoPortCfgEntry ::= SEQUENCE {
                       smTwoPortCfgIndex INTEGER,
                       smTwoPortCfgLabel OCTET STRING,
                       smTwoPortCfgType INTEGER,
                       smTwoPortCfgLinkSetting INTEGER,
                       smTwoPortCfgLinkState INTEGER,
                       smTwoPortCfgSpeedSetting OCTET STRING,
                       smTwoPortCfgSpeedStatus OCTET STRING,
                       smTwoPortCfgAvailSpeeds OCTET STRING
                       }
           
           smTwoPortCfgIndex OBJECT-TYPE
                       SYNTAX  Integer32 (0..2147483647) -- was INTEGER
                       MAX-ACCESS  read-only
                       STATUS  current -- was mandatory
                       DESCRIPTION
                       "Switch Module 2 port sequence index."
                       ::= { smTwoPortCfgEntry 1 }

           smTwoPortCfgLabel OBJECT-TYPE
                        SYNTAX  OCTET STRING
                        MAX-ACCESS  read-only
                        STATUS  current -- was mandatory
                        DESCRIPTION
                        "Switch Module 2 port label"
                        ::= { smTwoPortCfgEntry 2 }

           smTwoPortCfgType OBJECT-TYPE
                        SYNTAX  INTEGER {
                          unused(0),
                          externalPort(1), 
                          externalManagementPort(2),
                          externalDualPort(3),
                          bladePort(4),
                          mmManagementPort(5),
                          uplinkPort(6),
                          interModulePort(7),
                          interModuleManagementPort(8),
                          interModuleDualPort(9)
                        }
                        MAX-ACCESS  read-only
                        STATUS  current -- was mandatory
                        DESCRIPTION
                        "Switch Module 2 port type:
                        External port: This port is connected to external device and is for data traffic.
                        External management port: This port is solely for external management connection. 
                                This port is not used for data traffic from remote to blades.
                        External dual port: This external port is used for both data traffic to blades as well as for management.
                        Blade port: This port is connected to the blade.
                        Management Module Management port: This port is connected to the Management Module.
                        Uplink port: This port is configured for up link functionality.
                        Inter-Module port: This port is either by design connected to another I/O Module, 
                                by user configured, or by AMM setting the port type.
                        Inter-Module Management port: This port is connected to another I/O Module for management purpose.
                                The port type is either by design connected to another I/O Module, by user configured, 
                                or by AMM setting the port type.
                        Inter-Module Dual port:  The port is connected to another I/O Module and can be used for both data 
                                and management purposes. The port type is either by design connected to another I/O Module, 
                                by user configured, or by AMM setting the port type."
                        ::= { smTwoPortCfgEntry 3 }

           smTwoPortCfgLinkSetting OBJECT-TYPE
                        SYNTAX  INTEGER {
                          down(0),
                          up(1)
                        }
                        MAX-ACCESS  read-write
                        STATUS  current -- was mandatory
                        DESCRIPTION
                        "Current port link setting for Switch Module 2."
                        ::= { smTwoPortCfgEntry 4 }
                        
           smTwoPortCfgLinkState OBJECT-TYPE
                        SYNTAX  INTEGER {
                          down(0),
                          up(1)
                        }
                        MAX-ACCESS  read-only
                        STATUS  current -- was mandatory
                        DESCRIPTION
                        "Current port link state of Switch Module 2."
                        ::= { smTwoPortCfgEntry 5 }

           smTwoPortCfgSpeedSetting OBJECT-TYPE
                        SYNTAX  OCTET STRING
                        MAX-ACCESS  read-write
                        STATUS  current -- was mandatory
                        DESCRIPTION
                        "Set the port speed using the data rate and duplex value. For examples:
                        100mf: 100Mbps in Half Duplex;
                        10gf: 10 Gbps in Full Duplex;
                        auto: The working speed of the physical port can be tuned automatically.

                        NOTE: Only the speeds from smTwoPortCfgAvailSpeeds are applicable to setting
                        this mib object."
                        ::= { smTwoPortCfgEntry 6 }

           smTwoPortCfgSpeedStatus OBJECT-TYPE
                        SYNTAX  OCTET STRING
                        MAX-ACCESS  read-only
                        STATUS  current -- was mandatory
                        DESCRIPTION
                        "Current port speed of Switch Module 2."
                        ::= { smTwoPortCfgEntry 7 }
                        
           smTwoPortCfgAvailSpeeds OBJECT-TYPE
                        SYNTAX  OCTET STRING 
                        MAX-ACCESS  read-only
                        STATUS  current -- was mandatory
                        DESCRIPTION
                        "Available speed setting per port for Switch Module 2.
                        If there is more than one setting, the speeds are separated by a comma and then a space."
                        ::= { smTwoPortCfgEntry 8 }

         switchModThreePortCfg  OBJECT IDENTIFIER ::= { switchPortCfg 3 }
         
          smThreePortCfgTable OBJECT-TYPE
                      SYNTAX  SEQUENCE OF SmThreePortCfgEntry
                      MAX-ACCESS  not-accessible
                      STATUS  current -- was mandatory
                      DESCRIPTION
                      "Switch Module 3 port configuration information.
                      Note:  This option is not supported on all I/O modules."
                      ::= { switchModThreePortCfg 1 }

           smThreePortCfgEntry  OBJECT-TYPE
                         SYNTAX SmThreePortCfgEntry
                         MAX-ACCESS  not-accessible
                         STATUS  current -- was mandatory
                         DESCRIPTION
                         "Switch Module 3 port configuration information table entry"
                         INDEX { smThreePortCfgIndex }
                         ::= { smThreePortCfgTable 1 }

           SmThreePortCfgEntry ::= SEQUENCE {
                       smThreePortCfgIndex INTEGER,
                       smThreePortCfgLabel OCTET STRING,
                       smThreePortCfgType INTEGER,
                       smThreePortCfgLinkSetting INTEGER,
                       smThreePortCfgLinkState INTEGER,
                       smThreePortCfgSpeedSetting OCTET STRING,
                       smThreePortCfgSpeedStatus OCTET STRING,
                       smThreePortCfgAvailSpeeds OCTET STRING
                       }
           
           smThreePortCfgIndex OBJECT-TYPE
                       SYNTAX  Integer32 (0..2147483647) -- was INTEGER
                       MAX-ACCESS  read-only
                       STATUS  current -- was mandatory
                       DESCRIPTION
                       "Switch Module 3 port sequence index."
                       ::= { smThreePortCfgEntry 1 }

           smThreePortCfgLabel OBJECT-TYPE
                        SYNTAX  OCTET STRING
                        MAX-ACCESS  read-only
                        STATUS  current -- was mandatory
                        DESCRIPTION
                        "Switch Module 3 port label"
                        ::= { smThreePortCfgEntry 2 }

           smThreePortCfgType OBJECT-TYPE
                        SYNTAX  INTEGER {
                          unused(0),
                          externalPort(1), 
                          externalManagementPort(2),
                          externalDualPort(3),
                          bladePort(4),
                          mmManagementPort(5),
                          uplinkPort(6),
                          interModulePort(7),
                          interModuleManagementPort(8),
                          interModuleDualPort(9)
                        }
                        MAX-ACCESS  read-only
                        STATUS  current -- was mandatory
                        DESCRIPTION
                        "Switch Module 3 port type:
                        External port: This port is connected to external device and is for data traffic.
                        External management port: This port is solely for external management connection. 
                                This port is not used for data traffic from remote to blades.
                        External dual port: This external port is used for both data traffic to blades as well as for management.
                        Blade port: This port is connected to the blade.
                        Management Module Management port: This port is connected to the Management Module.
                        Uplink port: This port is configured for up link functionality.
                        Inter-Module port: This port is either by design connected to another I/O Module, 
                                by user configured, or by AMM setting the port type.
                        Inter-Module Management port: This port is connected to another I/O Module for management purpose.
                                The port type is either by design connected to another I/O Module, by user configured, 
                                or by AMM setting the port type.
                        Inter-Module Dual port:  The port is connected to another I/O Module and can be used for both data 
                                and management purposes. The port type is either by design connected to another I/O Module, 
                                by user configured, or by AMM setting the port type."
                        ::= { smThreePortCfgEntry 3 }

           smThreePortCfgLinkSetting OBJECT-TYPE
                        SYNTAX  INTEGER {
                          down(0),
                          up(1)
                        }
                        MAX-ACCESS  read-write
                        STATUS  current -- was mandatory
                        DESCRIPTION
                        "Current port link setting for Switch Module 3."
                        ::= { smThreePortCfgEntry 4 }
                        
           smThreePortCfgLinkState OBJECT-TYPE
                        SYNTAX  INTEGER {
                          down(0),
                          up(1)
                        }
                        MAX-ACCESS  read-only
                        STATUS  current -- was mandatory
                        DESCRIPTION
                        "Current port link state of Switch Module 3."
                        ::= { smThreePortCfgEntry 5 }

           smThreePortCfgSpeedSetting OBJECT-TYPE
                        SYNTAX  OCTET STRING
                        MAX-ACCESS  read-write
                        STATUS  current -- was mandatory
                        DESCRIPTION
                        "Set the port speed using the data rate and duplex value. For examples:
                        100mf: 100Mbps in Half Duplex;
                        10gf: 10 Gbps in Full Duplex;
                        auto: The working speed of the physical port can be tuned automatically.

                        NOTE: Only the speeds from smThreePortCfgAvailSpeeds are applicable to setting
                        this mib object."
                        ::= { smThreePortCfgEntry 6 }
                        
           smThreePortCfgSpeedStatus OBJECT-TYPE
                        SYNTAX  OCTET STRING
                        MAX-ACCESS  read-only
                        STATUS  current -- was mandatory
                        DESCRIPTION
                        "Current port speed of Switch Module 3."
                        ::= { smThreePortCfgEntry 7 }

           smThreePortCfgAvailSpeeds OBJECT-TYPE
                        SYNTAX  OCTET STRING 
                        MAX-ACCESS  read-only
                        STATUS  current -- was mandatory
                        DESCRIPTION
                        "Available speed setting per port for Switch Module 3.
                        If there is more than one setting, the speeds are separated by a comma and then a space."
                        ::= { smThreePortCfgEntry 8 }


         switchModFourPortCfg  OBJECT IDENTIFIER ::= { switchPortCfg 4 }
         
          smFourPortCfgTable OBJECT-TYPE
                      SYNTAX  SEQUENCE OF SmFourPortCfgEntry
                      MAX-ACCESS  not-accessible
                      STATUS  current -- was mandatory
                      DESCRIPTION
                      "Switch Module 4 port configuration information.
                      Note:  This option is not supported on all I/O modules."
                      ::= { switchModFourPortCfg 1 }

           smFourPortCfgEntry  OBJECT-TYPE
                         SYNTAX SmFourPortCfgEntry
                         MAX-ACCESS  not-accessible
                         STATUS  current -- was mandatory
                         DESCRIPTION
                         "Switch Module 4 port configuration information table entry"
                         INDEX { smFourPortCfgIndex }
                         ::= { smFourPortCfgTable 1 }

           SmFourPortCfgEntry ::= SEQUENCE {
                       smFourPortCfgIndex INTEGER,
                       smFourPortCfgLabel OCTET STRING,
                       smFourPortCfgType INTEGER,
                       smFourPortCfgLinkSetting INTEGER,
                       smFourPortCfgLinkState INTEGER,
                       smFourPortCfgSpeedSetting OCTET STRING,
                       smFourPortCfgSpeedStatus OCTET STRING,
                       smFourPortCfgAvailSpeeds OCTET STRING
                       }
           
           smFourPortCfgIndex OBJECT-TYPE
                       SYNTAX  Integer32 (0..2147483647) -- was INTEGER
                       MAX-ACCESS  read-only
                       STATUS  current -- was mandatory
                       DESCRIPTION
                       "Switch Module 4 port sequence index."
                       ::= { smFourPortCfgEntry 1 }

           smFourPortCfgLabel OBJECT-TYPE
                        SYNTAX  OCTET STRING
                        MAX-ACCESS  read-only
                        STATUS  current -- was mandatory
                        DESCRIPTION
                        "Switch Module 4 port label"
                        ::= { smFourPortCfgEntry 2 }

           smFourPortCfgType OBJECT-TYPE
                        SYNTAX  INTEGER {
                          unused(0),
                          externalPort(1), 
                          externalManagementPort(2),
                          externalDualPort(3),
                          bladePort(4),
                          mmManagementPort(5),
                          uplinkPort(6),
                          interModulePort(7),
                          interModuleManagementPort(8),
                          interModuleDualPort(9)
                        }
                        MAX-ACCESS  read-only
                        STATUS  current -- was mandatory
                        DESCRIPTION
                        "Switch Module 4 port type:
                        External port: This port is connected to external device and is for data traffic.
                        External management port: This port is solely for external management connection. 
                                This port is not used for data traffic from remote to blades.
                        External dual port: This external port is used for both data traffic to blades as well as for management.
                        Blade port: This port is connected to the blade.
                        Management Module Management port: This port is connected to the Management Module.
                        Uplink port: This port is configured for up link functionality.
                        Inter-Module port: This port is either by design connected to another I/O Module, 
                                by user configured, or by AMM setting the port type.
                        Inter-Module Management port: This port is connected to another I/O Module for management purpose.
                                The port type is either by design connected to another I/O Module, by user configured, 
                                or by AMM setting the port type.
                        Inter-Module Dual port:  The port is connected to another I/O Module and can be used for both data 
                                and management purposes. The port type is either by design connected to another I/O Module, 
                                by user configured, or by AMM setting the port type."
                        ::= { smFourPortCfgEntry 3 }

           smFourPortCfgLinkSetting OBJECT-TYPE
                        SYNTAX  INTEGER {
                          down(0),
                          up(1)
                        }
                        MAX-ACCESS  read-write
                        STATUS  current -- was mandatory
                        DESCRIPTION
                        "Current port link setting for Switch Module 4."
                        ::= { smFourPortCfgEntry 4 }

           smFourPortCfgLinkState OBJECT-TYPE
                        SYNTAX  INTEGER {
                          down(0),
                          up(1)
                        }
                        MAX-ACCESS  read-only
                        STATUS  current -- was mandatory
                        DESCRIPTION
                        "Current port link state of Switch Module 4."
                        ::= { smFourPortCfgEntry 5 }
                        
           smFourPortCfgSpeedSetting OBJECT-TYPE
                        SYNTAX  OCTET STRING
                        MAX-ACCESS  read-write
                        STATUS  current -- was mandatory
                        DESCRIPTION
                        "Set the port speed using the data rate and duplex value. For examples:
                        100mf: 100Mbps in Half Duplex;
                        10gf: 10 Gbps in Full Duplex;
                        auto: The working speed of the physical port can be tuned automatically.

                        NOTE: Only the speeds from smFourPortCfgAvailSpeeds are applicable to setting
                        this mib object."
                        ::= { smFourPortCfgEntry 6 }

           smFourPortCfgSpeedStatus OBJECT-TYPE
                        SYNTAX  OCTET STRING
                        MAX-ACCESS  read-only
                        STATUS  current -- was mandatory
                        DESCRIPTION
                        "Current port speed of Switch Module 4."
                        ::= { smFourPortCfgEntry 7 }
                        

           smFourPortCfgAvailSpeeds OBJECT-TYPE
                        SYNTAX  OCTET STRING 
                        MAX-ACCESS  read-only
                        STATUS  current -- was mandatory
                        DESCRIPTION
                        "Available speed setting per port for Switch Module 4.
                        If there is more than one setting, the speeds are separated by a comma and then a space."
                        ::= { smFourPortCfgEntry 8 }


         switchModFivePortCfg  OBJECT IDENTIFIER ::= { switchPortCfg 5 }
         
          smFivePortCfgTable OBJECT-TYPE
                      SYNTAX  SEQUENCE OF SmFivePortCfgEntry
                      MAX-ACCESS  not-accessible
                      STATUS  current -- was mandatory
                      DESCRIPTION
                      "Switch Module 5 port configuration information.
                      Note:  This option is not supported on all I/O modules."
                      ::= { switchModFivePortCfg 1 }

           smFivePortCfgEntry  OBJECT-TYPE
                         SYNTAX SmFivePortCfgEntry
                         MAX-ACCESS  not-accessible
                         STATUS  current -- was mandatory
                         DESCRIPTION
                         "Switch Module 5 port configuration information table entry"
                         INDEX { smFivePortCfgIndex }
                         ::= { smFivePortCfgTable 1 }

           SmFivePortCfgEntry ::= SEQUENCE {
                       smFivePortCfgIndex INTEGER,
                       smFivePortCfgLabel OCTET STRING,
                       smFivePortCfgType INTEGER,
                       smFivePortCfgLinkSetting INTEGER,
                       smFivePortCfgLinkState INTEGER,
                       smFivePortCfgSpeedSetting OCTET STRING,
                       smFivePortCfgSpeedStatus OCTET STRING,
                       smFivePortCfgAvailSpeeds OCTET STRING
                       }
           
           smFivePortCfgIndex OBJECT-TYPE
                       SYNTAX  Integer32 (0..2147483647) -- was INTEGER
                       MAX-ACCESS  read-only
                       STATUS  current -- was mandatory
                       DESCRIPTION
                       "Switch Module 5 port sequence index."
                       ::= { smFivePortCfgEntry 1 }

           smFivePortCfgLabel OBJECT-TYPE
                        SYNTAX  OCTET STRING
                        MAX-ACCESS  read-only
                        STATUS  current -- was mandatory
                        DESCRIPTION
                        "Switch Module 5 port label"
                        ::= { smFivePortCfgEntry 2 }

           smFivePortCfgType OBJECT-TYPE
                        SYNTAX  INTEGER {
                          unused(0),
                          externalPort(1), 
                          externalManagementPort(2),
                          externalDualPort(3),
                          bladePort(4),
                          mmManagementPort(5),
                          uplinkPort(6),
                          interModulePort(7),
                          interModuleManagementPort(8),
                          interModuleDualPort(9)
                        }
                        MAX-ACCESS  read-only
                        STATUS  current -- was mandatory
                        DESCRIPTION
                        "Switch Module 5 port type:
                        External port: This port is connected to external device and is for data traffic.
                        External management port: This port is solely for external management connection. 
                                This port is not used for data traffic from remote to blades.
                        External dual port: This external port is used for both data traffic to blades as well as for management.
                        Blade port: This port is connected to the blade.
                        Management Module Management port: This port is connected to the Management Module.
                        Uplink port: This port is configured for up link functionality.
                        Inter-Module port: This port is either by design connected to another I/O Module, 
                                by user configured, or by AMM setting the port type.
                        Inter-Module Management port: This port is connected to another I/O Module for management purpose.
                                The port type is either by design connected to another I/O Module, by user configured, 
                                or by AMM setting the port type.
                        Inter-Module Dual port:  The port is connected to another I/O Module and can be used for both data 
                                and management purposes. The port type is either by design connected to another I/O Module, 
                                by user configured, or by AMM setting the port type."
                        ::= { smFivePortCfgEntry 3 }

           smFivePortCfgLinkSetting OBJECT-TYPE
                        SYNTAX  INTEGER {
                          down(0),
                          up(1)
                        }
                        MAX-ACCESS  read-write
                        STATUS  current -- was mandatory
                        DESCRIPTION
                        "Current port link setting for Switch Module 5."
                        ::= { smFivePortCfgEntry 4 }

           smFivePortCfgLinkState OBJECT-TYPE
                        SYNTAX  INTEGER {
                          down(0),
                          up(1)
                        }
                        MAX-ACCESS  read-only
                        STATUS  current -- was mandatory
                        DESCRIPTION
                        "Current port link state of Switch Module 5."
                        ::= { smFivePortCfgEntry 5 }
                        
           smFivePortCfgSpeedSetting OBJECT-TYPE
                        SYNTAX  OCTET STRING
                        MAX-ACCESS  read-write
                        STATUS  current -- was mandatory
                        DESCRIPTION
                        "Set the port speed using the data rate and duplex value. For examples:
                        100mf: 100Mbps in Half Duplex;
                        10gf: 10 Gbps in Full Duplex;
                        auto: The working speed of the physical port can be tuned automatically.

                        NOTE: Only the speeds from smFivePortCfgAvailSpeeds are applicable to setting
                        this mib object."
                        ::= { smFivePortCfgEntry 6 }

           smFivePortCfgSpeedStatus OBJECT-TYPE
                        SYNTAX  OCTET STRING
                        MAX-ACCESS  read-only
                        STATUS  current -- was mandatory
                        DESCRIPTION
                        "Current port speed of Switch Module 5."
                        ::= { smFivePortCfgEntry 7 }

           smFivePortCfgAvailSpeeds OBJECT-TYPE
                        SYNTAX  OCTET STRING 
                        MAX-ACCESS  read-only
                        STATUS  current -- was mandatory
                        DESCRIPTION
                        "Available speed setting per port for Switch Module 5.
                        If there is more than one setting, the speeds are separated by a comma and then a space."
                        ::= { smFivePortCfgEntry 8 }


         switchModSixPortCfg  OBJECT IDENTIFIER ::= { switchPortCfg 6 }
         
          smSixPortCfgTable OBJECT-TYPE
                      SYNTAX  SEQUENCE OF SmSixPortCfgEntry
                      MAX-ACCESS  not-accessible
                      STATUS  current -- was mandatory
                      DESCRIPTION
                      "Switch Module 6 port configuration information.
                      Note:  This option is not supported on all I/O modules."
                      ::= { switchModSixPortCfg 1 }

           smSixPortCfgEntry  OBJECT-TYPE
                         SYNTAX SmSixPortCfgEntry
                         MAX-ACCESS  not-accessible
                         STATUS  current -- was mandatory
                         DESCRIPTION
                         "Switch Module 6 port configuration information table entry"
                         INDEX { smSixPortCfgIndex }
                         ::= { smSixPortCfgTable 1 }

           SmSixPortCfgEntry ::= SEQUENCE {
                       smSixPortCfgIndex INTEGER,
                       smSixPortCfgLabel OCTET STRING,
                       smSixPortCfgType INTEGER,
                       smSixPortCfgLinkSetting INTEGER,
                       smSixPortCfgLinkState INTEGER,
                       smSixPortCfgSpeedSetting OCTET STRING,
                       smSixPortCfgSpeedStatus OCTET STRING,
                       smSixPortCfgAvailSpeeds OCTET STRING
                       }
           
           smSixPortCfgIndex OBJECT-TYPE
                       SYNTAX  Integer32 (0..2147483647) -- was INTEGER
                       MAX-ACCESS  read-only
                       STATUS  current -- was mandatory
                       DESCRIPTION
                       "Switch Module 6 port sequence index."
                       ::= { smSixPortCfgEntry 1 }

           smSixPortCfgLabel OBJECT-TYPE
                        SYNTAX  OCTET STRING
                        MAX-ACCESS  read-only
                        STATUS  current -- was mandatory
                        DESCRIPTION
                        "Switch Module 6 port label"
                        ::= { smSixPortCfgEntry 2 }

           smSixPortCfgType OBJECT-TYPE
                        SYNTAX  INTEGER {
                          unused(0),
                          externalPort(1), 
                          externalManagementPort(2),
                          externalDualPort(3),
                          bladePort(4),
                          mmManagementPort(5),
                          uplinkPort(6),
                          interModulePort(7),
                          interModuleManagementPort(8),
                          interModuleDualPort(9)
                        }
                        MAX-ACCESS  read-only
                        STATUS  current -- was mandatory
                        DESCRIPTION
                        "Switch Module 6 port type:
                        External port: This port is connected to external device and is for data traffic.
                        External management port: This port is solely for external management connection. 
                                This port is not used for data traffic from remote to blades.
                        External dual port: This external port is used for both data traffic to blades as well as for management.
                        Blade port: This port is connected to the blade.
                        Management Module Management port: This port is connected to the Management Module.
                        Uplink port: This port is configured for up link functionality.
                        Inter-Module port: This port is either by design connected to another I/O Module, 
                                by user configured, or by AMM setting the port type.
                        Inter-Module Management port: This port is connected to another I/O Module for management purpose.
                                The port type is either by design connected to another I/O Module, by user configured, 
                                or by AMM setting the port type.
                        Inter-Module Dual port:  The port is connected to another I/O Module and can be used for both data 
                                and management purposes. The port type is either by design connected to another I/O Module, 
                                by user configured, or by AMM setting the port type."
                        ::= { smSixPortCfgEntry 3 }

           smSixPortCfgLinkSetting OBJECT-TYPE
                        SYNTAX  INTEGER {
                          down(0),
                          up(1)
                        }
                        MAX-ACCESS  read-write
                        STATUS  current -- was mandatory
                        DESCRIPTION
                        "Current port link setting for Switch Module 6."
                        ::= { smSixPortCfgEntry 4 }

           smSixPortCfgLinkState OBJECT-TYPE
                        SYNTAX  INTEGER {
                          down(0),
                          up(1)
                        }
                        MAX-ACCESS  read-only
                        STATUS  current -- was mandatory
                        DESCRIPTION
                        "Current port link state of Switch Module 6."
                        ::= { smSixPortCfgEntry 5 }
                        
           smSixPortCfgSpeedSetting OBJECT-TYPE
                        SYNTAX  OCTET STRING
                        MAX-ACCESS  read-write
                        STATUS  current -- was mandatory
                        DESCRIPTION
                        "Set the port speed using the data rate and duplex value. For examples:
                        100mf: 100Mbps in Half Duplex;
                        10gf: 10 Gbps in Full Duplex;
                        auto: The working speed of the physical port can be tuned automatically.

                        NOTE: Only the speeds from smSixPortCfgAvailSpeeds are applicable to setting
                        this mib object."
                        ::= { smSixPortCfgEntry 6 }

           smSixPortCfgSpeedStatus OBJECT-TYPE
                        SYNTAX  OCTET STRING
                        MAX-ACCESS  read-only
                        STATUS  current -- was mandatory
                        DESCRIPTION
                        "Current port speed of Switch Module 6."
                        ::= { smSixPortCfgEntry 7 }
                        
           smSixPortCfgAvailSpeeds OBJECT-TYPE
                        SYNTAX  OCTET STRING 
                        MAX-ACCESS  read-only
                        STATUS  current -- was mandatory
                        DESCRIPTION
                        "Available speed setting per port for Switch Module 6.
                        If there is more than one setting, the speeds are separated by a comma and then a space."
                        ::= { smSixPortCfgEntry 8 }


         switchModSevenPortCfg  OBJECT IDENTIFIER ::= { switchPortCfg 7 }
          
          smSevenPortCfgTable OBJECT-TYPE
                      SYNTAX  SEQUENCE OF SmSevenPortCfgEntry
                      MAX-ACCESS  not-accessible
                      STATUS  current -- was mandatory
                      DESCRIPTION
                      "Switch Module 7 port configuration information.
                      Note:  This option is not supported on all I/O modules."
                      ::= { switchModSevenPortCfg 1 }

           smSevenPortCfgEntry  OBJECT-TYPE
                         SYNTAX SmSevenPortCfgEntry
                         MAX-ACCESS  not-accessible
                         STATUS  current -- was mandatory
                         DESCRIPTION
                         "Switch Module 7 port configuration information table entry"
                         INDEX { smSevenPortCfgIndex }
                         ::= { smSevenPortCfgTable 1 }

           SmSevenPortCfgEntry ::= SEQUENCE {
                       smSevenPortCfgIndex INTEGER,
                       smSevenPortCfgLabel OCTET STRING,
                       smSevenPortCfgType INTEGER,
                       smSevenPortCfgLinkSetting INTEGER,
                       smSevenPortCfgLinkState INTEGER,
                       smSevenPortCfgSpeedSetting OCTET STRING,
                       smSevenPortCfgSpeedStatus OCTET STRING,
                       smSevenPortCfgAvailSpeeds OCTET STRING
                       }
           
           smSevenPortCfgIndex OBJECT-TYPE
                       SYNTAX  Integer32 (0..2147483647) -- was INTEGER
                       MAX-ACCESS  read-only
                       STATUS  current -- was mandatory
                       DESCRIPTION
                       "Switch Module 7 port sequence index."
                       ::= { smSevenPortCfgEntry 1 }

           smSevenPortCfgLabel OBJECT-TYPE
                        SYNTAX  OCTET STRING
                        MAX-ACCESS  read-only
                        STATUS  current -- was mandatory
                        DESCRIPTION
                        "Switch Module 7 port label"
                        ::= { smSevenPortCfgEntry 2 }

           smSevenPortCfgType OBJECT-TYPE
                        SYNTAX  INTEGER {
                          unused(0),
                          externalPort(1), 
                          externalManagementPort(2),
                          externalDualPort(3),
                          bladePort(4),
                          mmManagementPort(5),
                          uplinkPort(6),
                          interModulePort(7),
                          interModuleManagementPort(8),
                          interModuleDualPort(9)
                        }
                        MAX-ACCESS  read-only
                        STATUS  current -- was mandatory
                        DESCRIPTION
                        "Switch Module 7 port type:
                        External port: This port is connected to external device and is for data traffic.
                        External management port: This port is solely for external management connection. 
                                This port is not used for data traffic from remote to blades.
                        External dual port: This external port is used for both data traffic to blades as well as for management.
                        Blade port: This port is connected to the blade.
                        Management Module Management port: This port is connected to the Management Module.
                        Uplink port: This port is configured for up link functionality.
                        Inter-Module port: This port is either by design connected to another I/O Module, 
                                by user configured, or by AMM setting the port type.
                        Inter-Module Management port: This port is connected to another I/O Module for management purpose.
                                The port type is either by design connected to another I/O Module, by user configured, 
                                or by AMM setting the port type.
                        Inter-Module Dual port:  The port is connected to another I/O Module and can be used for both data 
                                and management purposes. The port type is either by design connected to another I/O Module, 
                                by user configured, or by AMM setting the port type."
                        ::= { smSevenPortCfgEntry 3 }

           smSevenPortCfgLinkSetting OBJECT-TYPE
                        SYNTAX  INTEGER {
                          down(0),
                          up(1)
                        }
                        MAX-ACCESS  read-write
                        STATUS  current -- was mandatory
                        DESCRIPTION
                        "Current port link setting for Switch Module 7."
                        ::= { smSevenPortCfgEntry 4 }

           smSevenPortCfgLinkState OBJECT-TYPE
                        SYNTAX  INTEGER {
                          down(0),
                          up(1)
                        }
                        MAX-ACCESS  read-only
                        STATUS  current -- was mandatory
                        DESCRIPTION
                        "Current port link state of Switch Module 7."
                        ::= { smSevenPortCfgEntry 5 }
                        
           smSevenPortCfgSpeedSetting OBJECT-TYPE
                        SYNTAX  OCTET STRING
                        MAX-ACCESS  read-write
                        STATUS  current -- was mandatory
                        DESCRIPTION
                        "Set the port speed using the data rate and duplex value. For examples:
                        100mf: 100Mbps in Half Duplex;
                        10gf: 10 Gbps in Full Duplex;
                        auto: The working speed of the physical port can be tuned automatically.

                        NOTE: Only the speeds from smSevenPortCfgAvailSpeeds are applicable to setting
                        this mib object."
                        ::= { smSevenPortCfgEntry 6 }

           smSevenPortCfgSpeedStatus OBJECT-TYPE
                        SYNTAX  OCTET STRING
                        MAX-ACCESS  read-only
                        STATUS  current -- was mandatory
                        DESCRIPTION
                        "Current port speed of Switch Module 7."
                        ::= { smSevenPortCfgEntry 7 }
                        
           smSevenPortCfgAvailSpeeds OBJECT-TYPE
                        SYNTAX  OCTET STRING 
                        MAX-ACCESS  read-only
                        STATUS  current -- was mandatory
                        DESCRIPTION
                        "Available speed setting per port for Switch Module 7.
                        If there is more than one setting, the speeds are separated by a comma and then a space."
                        ::= { smSevenPortCfgEntry 8 }


         switchModEightPortCfg  OBJECT IDENTIFIER ::= { switchPortCfg 8 }
          
          smEightPortCfgTable OBJECT-TYPE
                      SYNTAX  SEQUENCE OF SmEightPortCfgEntry
                      MAX-ACCESS  not-accessible
                      STATUS  current -- was mandatory
                      DESCRIPTION
                      "Switch Module 8 port configuration information.
                      Note:  This option is not supported on all I/O modules."
                      ::= { switchModEightPortCfg 1 }

           smEightPortCfgEntry  OBJECT-TYPE
                         SYNTAX SmEightPortCfgEntry
                         MAX-ACCESS  not-accessible
                         STATUS  current -- was mandatory
                         DESCRIPTION
                         "Switch Module 8 port configuration information table entry"
                         INDEX { smEightPortCfgIndex }
                         ::= { smEightPortCfgTable 1 }

           SmEightPortCfgEntry ::= SEQUENCE {
                       smEightPortCfgIndex INTEGER,
                       smEightPortCfgLabel OCTET STRING,
                       smEightPortCfgType INTEGER,
                       smEightPortCfgLinkSetting INTEGER,
                       smEightPortCfgLinkState INTEGER,
                       smEightPortCfgSpeedSetting OCTET STRING,
                       smEightPortCfgSpeedStatus OCTET STRING,
                       smEightPortCfgAvailSpeeds OCTET STRING
                       }
           
           smEightPortCfgIndex OBJECT-TYPE
                       SYNTAX  Integer32 (0..2147483647) -- was INTEGER
                       MAX-ACCESS  read-only
                       STATUS  current -- was mandatory
                       DESCRIPTION
                       "Switch Module 8 port sequence index."
                       ::= { smEightPortCfgEntry 1 }

           smEightPortCfgLabel OBJECT-TYPE
                        SYNTAX  OCTET STRING
                        MAX-ACCESS  read-only
                        STATUS  current -- was mandatory
                        DESCRIPTION
                        "Switch Module 8 port label"
                        ::= { smEightPortCfgEntry 2 }

           smEightPortCfgType OBJECT-TYPE
                        SYNTAX  INTEGER {
                          unused(0),
                          externalPort(1), 
                          externalManagementPort(2),
                          externalDualPort(3),
                          bladePort(4),
                          mmManagementPort(5),
                          uplinkPort(6),
                          interModulePort(7),
                          interModuleManagementPort(8),
                          interModuleDualPort(9)
                        }
                        MAX-ACCESS  read-only
                        STATUS  current -- was mandatory
                        DESCRIPTION
                        "Switch Module 8 port type:
                        External port: This port is connected to external device and is for data traffic.
                        External management port: This port is solely for external management connection. 
                                This port is not used for data traffic from remote to blades.
                        External dual port: This external port is used for both data traffic to blades as well as for management.
                        Blade port: This port is connected to the blade.
                        Management Module Management port: This port is connected to the Management Module.
                        Uplink port: This port is configured for up link functionality.
                        Inter-Module port: This port is either by design connected to another I/O Module, 
                                by user configured, or by AMM setting the port type.
                        Inter-Module Management port: This port is connected to another I/O Module for management purpose.
                                The port type is either by design connected to another I/O Module, by user configured, 
                                or by AMM setting the port type.
                        Inter-Module Dual port:  The port is connected to another I/O Module and can be used for both data 
                                and management purposes. The port type is either by design connected to another I/O Module, 
                                by user configured, or by AMM setting the port type."
                        ::= { smEightPortCfgEntry 3 }

           smEightPortCfgLinkSetting OBJECT-TYPE
                        SYNTAX  INTEGER {
                          down(0),
                          up(1)
                        }
                        MAX-ACCESS  read-write
                        STATUS  current -- was mandatory
                        DESCRIPTION
                        "Current port link setting for Switch Module 8."
                        ::= { smEightPortCfgEntry 4 }

           smEightPortCfgLinkState OBJECT-TYPE
                        SYNTAX  INTEGER {
                          down(0),
                          up(1)
                        }
                        MAX-ACCESS  read-only
                        STATUS  current -- was mandatory
                        DESCRIPTION
                        "Current port link state of Switch Module 8."
                        ::= { smEightPortCfgEntry 5 }
                        
           smEightPortCfgSpeedSetting OBJECT-TYPE
                        SYNTAX  OCTET STRING
                        MAX-ACCESS  read-write
                        STATUS  current -- was mandatory
                        DESCRIPTION
                        "Set the port speed using the data rate and duplex value. For examples:
                        100mf: 100Mbps in Half Duplex;
                        10gf: 10 Gbps in Full Duplex;
                        auto: The working speed of the physical port can be tuned automatically.

                        NOTE: Only the speeds from smEightPortCfgAvailSpeeds are applicable to setting
                        this mib object."
                        ::= { smEightPortCfgEntry 6 }

           smEightPortCfgSpeedStatus OBJECT-TYPE
                        SYNTAX  OCTET STRING
                        MAX-ACCESS  read-only
                        STATUS  current -- was mandatory
                        DESCRIPTION
                        "Current port speed of Switch Module 8."
                        ::= { smEightPortCfgEntry 7 }

           smEightPortCfgAvailSpeeds OBJECT-TYPE
                        SYNTAX  OCTET STRING 
                        MAX-ACCESS  read-only
                        STATUS  current -- was mandatory
                        DESCRIPTION
                        "Available speed setting per port for Switch Module 8.
                        If there is more than one setting, the speeds are separated by a comma and then a space."
                        ::= { smEightPortCfgEntry 8 }


         switchModNinePortCfg  OBJECT IDENTIFIER ::= { switchPortCfg 9 }
          
          smNinePortCfgTable OBJECT-TYPE
                      SYNTAX  SEQUENCE OF SmNinePortCfgEntry
                      MAX-ACCESS  not-accessible
                      STATUS  current -- was mandatory
                      DESCRIPTION
                      "Switch Module 9 port configuration information.
                      Note:  This option is not supported on all I/O modules."
                      ::= { switchModNinePortCfg 1 }

           smNinePortCfgEntry  OBJECT-TYPE
                         SYNTAX SmNinePortCfgEntry
                         MAX-ACCESS  not-accessible
                         STATUS  current -- was mandatory
                         DESCRIPTION
                         "Switch Module 9 port configuration information table entry"
                         INDEX { smNinePortCfgIndex }
                         ::= { smNinePortCfgTable 1 }

           SmNinePortCfgEntry ::= SEQUENCE {
                       smNinePortCfgIndex INTEGER,
                       smNinePortCfgLabel OCTET STRING,
                       smNinePortCfgType INTEGER,
                       smNinePortCfgLinkSetting INTEGER,
                       smNinePortCfgLinkState INTEGER,
                       smNinePortCfgSpeedSetting OCTET STRING,
                       smNinePortCfgSpeedStatus OCTET STRING,
                       smNinePortCfgAvailSpeeds OCTET STRING
                       }
           
           smNinePortCfgIndex OBJECT-TYPE
                       SYNTAX  Integer32 (0..2147483647) -- was INTEGER
                       MAX-ACCESS  read-only
                       STATUS  current -- was mandatory
                       DESCRIPTION
                       "Switch Module 9 port sequence index."
                       ::= { smNinePortCfgEntry 1 }

           smNinePortCfgLabel OBJECT-TYPE
                        SYNTAX  OCTET STRING
                        MAX-ACCESS  read-only
                        STATUS  current -- was mandatory
                        DESCRIPTION
                        "Switch Module 9 port label"
                        ::= { smNinePortCfgEntry 2 }

           smNinePortCfgType OBJECT-TYPE
                        SYNTAX  INTEGER {
                          unused(0),
                          externalPort(1), 
                          externalManagementPort(2),
                          externalDualPort(3),
                          bladePort(4),
                          mmManagementPort(5),
                          uplinkPort(6),
                          interModulePort(7),
                          interModuleManagementPort(8),
                          interModuleDualPort(9)
                        }
                        MAX-ACCESS  read-only
                        STATUS  current -- was mandatory
                        DESCRIPTION
                        "Switch Module 9 port type:
                        External port: This port is connected to external device and is for data traffic.
                        External management port: This port is solely for external management connection. 
                                This port is not used for data traffic from remote to blades.
                        External dual port: This external port is used for both data traffic to blades as well as for management.
                        Blade port: This port is connected to the blade.
                        Management Module Management port: This port is connected to the Management Module.
                        Uplink port: This port is configured for up link functionality.
                        Inter-Module port: This port is either by design connected to another I/O Module, 
                                by user configured, or by AMM setting the port type.
                        Inter-Module Management port: This port is connected to another I/O Module for management purpose.
                                The port type is either by design connected to another I/O Module, by user configured, 
                                or by AMM setting the port type.
                        Inter-Module Dual port:  The port is connected to another I/O Module and can be used for both data 
                                and management purposes. The port type is either by design connected to another I/O Module, 
                                by user configured, or by AMM setting the port type."
                        ::= { smNinePortCfgEntry 3 }

           smNinePortCfgLinkSetting OBJECT-TYPE
                        SYNTAX  INTEGER {
                          down(0),
                          up(1)
                        }
                        MAX-ACCESS  read-write
                        STATUS  current -- was mandatory
                        DESCRIPTION
                        "Current port link setting for Switch Module 9."
                        ::= { smNinePortCfgEntry 4 }

           smNinePortCfgLinkState OBJECT-TYPE
                        SYNTAX  INTEGER {
                          down(0),
                          up(1)
                        }
                        MAX-ACCESS  read-only
                        STATUS  current -- was mandatory
                        DESCRIPTION
                        "Current port link state of Switch Module 9."
                        ::= { smNinePortCfgEntry 5 }
                        
           smNinePortCfgSpeedSetting OBJECT-TYPE
                        SYNTAX  OCTET STRING
                        MAX-ACCESS  read-write
                        STATUS  current -- was mandatory
                        DESCRIPTION
                        "Set the port speed using the data rate and duplex value. For examples:
                        100mf: 100Mbps in Half Duplex;
                        10gf: 10 Gbps in Full Duplex;
                        auto: The working speed of the physical port can be tuned automatically.

                        NOTE: Only the speeds from smNinePortCfgAvailSpeeds are applicable to setting
                        this mib object."
                        ::= { smNinePortCfgEntry 6 }

           smNinePortCfgSpeedStatus OBJECT-TYPE
                        SYNTAX  OCTET STRING
                        MAX-ACCESS  read-only
                        STATUS  current -- was mandatory
                        DESCRIPTION
                        "Current port speed of Switch Module 9."
                        ::= { smNinePortCfgEntry 7 }
                        
           smNinePortCfgAvailSpeeds OBJECT-TYPE
                        SYNTAX  OCTET STRING 
                        MAX-ACCESS  read-only
                        STATUS  current -- was mandatory
                        DESCRIPTION
                        "Available speed setting per port for Switch Module 9.
                        If there is more than one setting, the speeds are separated by a comma and then a space."
                        ::= { smNinePortCfgEntry 8 }


         switchModTenPortCfg  OBJECT IDENTIFIER ::= { switchPortCfg 10 }
          
          smTenPortCfgTable OBJECT-TYPE
                      SYNTAX  SEQUENCE OF SmTenPortCfgEntry
                      MAX-ACCESS  not-accessible
                      STATUS  current -- was mandatory
                      DESCRIPTION
                      "Switch Module 10 port configuration information.
                      Note:  This option is not supported on all I/O modules."
                      ::= { switchModTenPortCfg 1 }

           smTenPortCfgEntry  OBJECT-TYPE
                         SYNTAX SmTenPortCfgEntry
                         MAX-ACCESS  not-accessible
                         STATUS  current -- was mandatory
                         DESCRIPTION
                         "Switch Module 10 port configuration information table entry"
                         INDEX { smTenPortCfgIndex }
                         ::= { smTenPortCfgTable 1 }

           SmTenPortCfgEntry ::= SEQUENCE {
                       smTenPortCfgIndex INTEGER,
                       smTenPortCfgLabel OCTET STRING,
                       smTenPortCfgType INTEGER,
                       smTenPortCfgLinkSetting INTEGER,
                       smTenPortCfgLinkState INTEGER,
                       smTenPortCfgSpeedSetting OCTET STRING,
                       smTenPortCfgSpeedStatus OCTET STRING,
                       smTenPortCfgAvailSpeeds OCTET STRING
                       }
           
           smTenPortCfgIndex OBJECT-TYPE
                       SYNTAX  Integer32 (0..2147483647) -- was INTEGER
                       MAX-ACCESS  read-only
                       STATUS  current -- was mandatory
                       DESCRIPTION
                       "Switch Module 10 port sequence index."
                       ::= { smTenPortCfgEntry 1 }

           smTenPortCfgLabel OBJECT-TYPE
                        SYNTAX  OCTET STRING
                        MAX-ACCESS  read-only
                        STATUS  current -- was mandatory
                        DESCRIPTION
                        "Switch Module 10 port label"
                        ::= { smTenPortCfgEntry 2 }

           smTenPortCfgType OBJECT-TYPE
                        SYNTAX  INTEGER {
                          unused(0),
                          externalPort(1), 
                          externalManagementPort(2),
                          externalDualPort(3),
                          bladePort(4),
                          mmManagementPort(5),
                          uplinkPort(6),
                          interModulePort(7),
                          interModuleManagementPort(8),
                          interModuleDualPort(9)
                        }
                        MAX-ACCESS  read-only
                        STATUS  current -- was mandatory
                        DESCRIPTION
                        "Switch Module 10 port type:
                        External port: This port is connected to external device and is for data traffic.
                        External management port: This port is solely for external management connection. 
                                This port is not used for data traffic from remote to blades.
                        External dual port: This external port is used for both data traffic to blades as well as for management.
                        Blade port: This port is connected to the blade.
                        Management Module Management port: This port is connected to the Management Module.
                        Uplink port: This port is configured for up link functionality.
                        Inter-Module port: This port is either by design connected to another I/O Module, 
                                by user configured, or by AMM setting the port type.
                        Inter-Module Management port: This port is connected to another I/O Module for management purpose.
                                The port type is either by design connected to another I/O Module, by user configured, 
                                or by AMM setting the port type.
                        Inter-Module Dual port:  The port is connected to another I/O Module and can be used for both data 
                                and management purposes. The port type is either by design connected to another I/O Module, 
                                by user configured, or by AMM setting the port type."
                        ::= { smTenPortCfgEntry 3 }

           smTenPortCfgLinkSetting OBJECT-TYPE
                        SYNTAX  INTEGER {
                          down(0),
                          up(1)
                        }
                        MAX-ACCESS  read-write
                        STATUS  current -- was mandatory
                        DESCRIPTION
                        "Current port link setting for Switch Module 10."
                        ::= { smTenPortCfgEntry 4 }

           smTenPortCfgLinkState OBJECT-TYPE
                        SYNTAX  INTEGER {
                          down(0),
                          up(1)
                        }
                        MAX-ACCESS  read-only
                        STATUS  current -- was mandatory
                        DESCRIPTION
                        "Current port link state of Switch Module 10."
                        ::= { smTenPortCfgEntry 5 }
                        
           smTenPortCfgSpeedSetting OBJECT-TYPE
                        SYNTAX  OCTET STRING
                        MAX-ACCESS  read-write
                        STATUS  current -- was mandatory
                        DESCRIPTION
                        "Set the port speed using the data rate and duplex value. For examples:
                        100mf: 100Mbps in Half Duplex;
                        10gf: 10 Gbps in Full Duplex;
                        auto: The working speed of the physical port can be tuned automatically.

                        NOTE: Only the speeds from smTenPortCfgAvailSpeeds are applicable to setting
                        this mib object."
                        ::= { smTenPortCfgEntry 6 }

           smTenPortCfgSpeedStatus OBJECT-TYPE
                        SYNTAX  OCTET STRING
                        MAX-ACCESS  read-only
                        STATUS  current -- was mandatory
                        DESCRIPTION
                        "Current port speed of Switch Module 10."
                        ::= { smTenPortCfgEntry 7 }
                        
           smTenPortCfgAvailSpeeds OBJECT-TYPE
                        SYNTAX  OCTET STRING 
                        MAX-ACCESS  read-only
                        STATUS  current -- was mandatory
                        DESCRIPTION
                        "Available speed setting per port for Switch Module 10.
                        If there is more than one setting, the speeds are separated by a comma and then a space."
                        ::= { smTenPortCfgEntry 8 }


       -- ********************************************************************************
       -- RAID Controller config
       -- ********************************************************************************
       raidControllerConfig OBJECT IDENTIFIER ::= { switchModule 3 }

        raidControllerTable OBJECT-TYPE
                    SYNTAX  SEQUENCE OF RaidControllerEntry
                    MAX-ACCESS  not-accessible
                    STATUS  current -- was mandatory
                    DESCRIPTION
                    "RAID Controller control table."
                    ::= { raidControllerConfig 1 }

         raidControllerEntry  OBJECT-TYPE
                       SYNTAX RaidControllerEntry
                       MAX-ACCESS  not-accessible
                       STATUS  current -- was mandatory
                       DESCRIPTION
                       "RAID Controller control table entry."
                       INDEX { raidControllerIndex }
                       ::= { raidControllerTable 1 }

         RaidControllerEntry ::= SEQUENCE {
                     raidControllerIndex INTEGER,
                     raidControllerId INTEGER,
                     raidControllerExists INTEGER,
                     raidControllerPowerState INTEGER,
                     raidControllerMACAddress OCTET STRING,
                     raidControllerSasID OCTET STRING,
                     raidControllerPingRequest INTEGER
                     }

         raidControllerIndex OBJECT-TYPE
                     SYNTAX  Integer32 (0..2147483647) -- was INTEGER
                     MAX-ACCESS  read-only
                     STATUS  current -- was mandatory
                     DESCRIPTION
                     "RAID Controller control table index.
                      This MIB object is for SAS Controller Modules only."
                     ::= { raidControllerEntry 1 }

         raidControllerId OBJECT-TYPE
                     SYNTAX  INTEGER {
                         module3(3),
                         module4(4)
                       }
                     MAX-ACCESS  read-only
                     STATUS  current -- was mandatory
                     DESCRIPTION
                     "The I/O Module numeric identifier for the SAS Controller Module.
                      This MIB object is for SAS Controller Modules only."
                     ::= { raidControllerEntry 2 }
                     
         raidControllerExists OBJECT-TYPE
                     SYNTAX  INTEGER {
                         false(0),
                         true(1)
                     }
                     MAX-ACCESS  read-only
                     STATUS  current -- was mandatory
                     DESCRIPTION
                     "Indicates whether the I/O Module specified for the RAID Controller
                     exists or not.
                      This MIB object is for SAS Controller Modules only."
                     ::= { raidControllerEntry 3 }
                     
         raidControllerPowerState OBJECT-TYPE
                     SYNTAX  INTEGER {
                         off(0),
                         on(1),
                         shutdownInProgress(2)
                     }
                     MAX-ACCESS  read-only
                     STATUS  current -- was mandatory
                     DESCRIPTION
                     "Indicates whether the I/O Module is powered on or not.
                     This MIB object is for SAS Controller Modules only."
                     ::= { raidControllerEntry 4 }

         raidControllerMACAddress OBJECT-TYPE
                     SYNTAX  OCTET STRING
                     MAX-ACCESS  read-only
                     STATUS  current -- was mandatory
                     DESCRIPTION
                     "The MAC address for the RAID Controller network interface.
                      This MIB object is for SAS Controller Modules only."
                     ::= { raidControllerEntry 5 }

         raidControllerSasID OBJECT-TYPE
                     SYNTAX  OCTET STRING
                     MAX-ACCESS  read-only
                     STATUS  current -- was mandatory
                     DESCRIPTION
                     "The hardware VPD SAS ID for the RAID Controller network interface.
                      This MIB object is for SAS Controller Modules only."
                     ::= { raidControllerEntry 6 }

         raidControllerPingRequest OBJECT-TYPE
                     SYNTAX  INTEGER
                     MAX-ACCESS  read-write
                     STATUS  current -- was mandatory
                     DESCRIPTION
                     "Sends a ping to the current IP address of the RAID Controller network interface.
                      This MIB object can not be set, if AMM grants I/O Module the Protected Mode
                      permission and the module goes into Protected Mode.
                      NOTE: Value returned for the GET command is meaningless for this MIB object
                      This MIB object is for SAS Controller Modules only."
                     ::= { raidControllerEntry 7 }

        raidControllerNetworkCfg OBJECT IDENTIFIER ::= { raidControllerConfig 2 }

           rcCurrentIPInfoTable OBJECT-TYPE
                      SYNTAX  SEQUENCE OF RcCurrentIPInfoEntry
                      MAX-ACCESS  not-accessible
                      STATUS  current -- was mandatory
                      DESCRIPTION
                      "RAID Controller current IP table.
                       This MIB object is for SAS Controller Modules only."
                      ::= { raidControllerNetworkCfg 1 }

           rcCurrentIPInfoEntry  OBJECT-TYPE
                     SYNTAX RcCurrentIPInfoEntry
                     MAX-ACCESS  not-accessible
                     STATUS  current -- was mandatory
                     DESCRIPTION
                     "RAID Controller current IP table entry.
                      This MIB object is for SAS Controller Modules only."
                      INDEX { rcCurrentIPInfoIndex }
                      ::= { rcCurrentIPInfoTable 1 }

           RcCurrentIPInfoEntry ::= SEQUENCE {
                       rcCurrentIPInfoIndex INTEGER,
                       rcCurrentIPInfoId INTEGER,
                       rcCurrentIPInfoExists INTEGER,
                       rcCurrentIPInfoPowerState INTEGER,
                       rcCurrentIPAddr IpAddress,
                       rcCurrentSubnetMask IpAddress,
                       rcCurrentGateway IpAddress,
                       rcCurrentIPConfigMethod INTEGER,
                       rcCurrentRaidedVlanId INTEGER
                       }

           rcCurrentIPInfoIndex OBJECT-TYPE
                       SYNTAX  Integer32 (0..2147483647) -- was INTEGER
                       MAX-ACCESS  read-only
                       STATUS  current -- was mandatory
                       DESCRIPTION
                       "RAID Controller current IP table index.
                        This MIB object is for SAS Controller Modules only."
                       ::= { rcCurrentIPInfoEntry 1 }

           rcCurrentIPInfoId OBJECT-TYPE
                       SYNTAX  INTEGER {
                         module3(3),
                         module4(4)
                       }
                       MAX-ACCESS  read-only
                       STATUS  current -- was mandatory
                       DESCRIPTION
                      "The I/O Module numeric identifier for the RAID Controller.
                       This MIB object is for SAS Controller Modules only."
                      ::= { rcCurrentIPInfoEntry 2 }

           rcCurrentIPInfoExists OBJECT-TYPE
                       SYNTAX  INTEGER {
                         false(0),
                         true(1)
                       }
                       MAX-ACCESS  read-only
                       STATUS  current -- was mandatory
                       DESCRIPTION
                       "Indicates whether the I/O Module exists or not.
                        This MIB object is for SAS Controller Modules only."
                       ::= { rcCurrentIPInfoEntry 3 }

           rcCurrentIPInfoPowerState OBJECT-TYPE
                       SYNTAX  INTEGER {
                         off(0),
                         on(1),
                         shutdownInProgress(2)
                       }
                       MAX-ACCESS  read-only
                       STATUS  current -- was mandatory
                       DESCRIPTION
                       "Indicates whether the I/O Module is powered on or not.
                        This MIB object is for SAS Controller Modules only."
                       ::= { rcCurrentIPInfoEntry 4 }

           rcCurrentIPAddr OBJECT-TYPE
                        SYNTAX  IpAddress
                        MAX-ACCESS  read-only
                        STATUS  current -- was mandatory
                        DESCRIPTION
                        "The current IP address for the RAID Controller network interface.
                         This MIB object is for SAS Controller Modules only."
                        ::= { rcCurrentIPInfoEntry 5 }


           rcCurrentSubnetMask OBJECT-TYPE
                        SYNTAX  IpAddress
                        MAX-ACCESS  read-only
                        STATUS  current -- was mandatory
                        DESCRIPTION
                        "The current subnet mask for the RAID Controller network interface.
                         This MIB object is for SAS Controller Modules only."
                        ::= { rcCurrentIPInfoEntry 6 }

          rcCurrentGateway OBJECT-TYPE
                       SYNTAX  IpAddress
                       MAX-ACCESS  read-only
                       STATUS  current -- was mandatory
                       DESCRIPTION
                       "The current subnet mask for the RAID Controller network interface.
                        This MIB object is for SAS Controller Modules only."
                       ::= { rcCurrentIPInfoEntry 7 }

          rcCurrentIPConfigMethod OBJECT-TYPE
                       SYNTAX  INTEGER {
                         unknown(0),
                         static(1),
                         dhcp(2)
                       }
                       MAX-ACCESS  read-only
                       STATUS  current -- was mandatory
                       DESCRIPTION
                       "The current IP gateway for the RAID Controller network interface.
                       This MIB object is for SAS Controller Modules only."
                       ::= { rcCurrentIPInfoEntry 8 }

          rcCurrentRaidedVlanId   OBJECT-TYPE
                       SYNTAX  INTEGER
                       MAX-ACCESS  read-only
                       STATUS  current -- was mandatory
                       DESCRIPTION
                       "The current virtual LAN ID for the RAID Controller network interface.
                       This MIB object is for SAS Controller Modules only."
                       ::= { rcCurrentIPInfoEntry 9 }

          rcNewIPInfoTable OBJECT-TYPE
                      SYNTAX  SEQUENCE OF RcNewIPInfoEntry
                      MAX-ACCESS  not-accessible
                      STATUS  current -- was mandatory
                      DESCRIPTION
                      "RAID Controller new IP configuration table.
                       This MIB object is for SAS Controller Modules only.
                       NOTE: This MIB object is not applicable to modules that are running in Network Address 
                       Translation (NAT) Mode."
                      ::= { raidControllerNetworkCfg 2 }

           rcNewIPInfoEntry  OBJECT-TYPE
                         SYNTAX RcNewIPInfoEntry
                         MAX-ACCESS  not-accessible
                         STATUS  current -- was mandatory
                         DESCRIPTION
                         "RAID Controller new IP configuration information table entry.
                          This MIB object is for SAS Controller Modules only.
                          NOTE: This MIB table is not applicable to modules that are running in Network Address 
                          Translation (NAT) Mode."
                         INDEX { rcNewIPInfoIndex }
                         ::= { rcNewIPInfoTable 1 }

           RcNewIPInfoEntry ::= SEQUENCE {
                       rcNewIPInfoIndex INTEGER,
                       rcNewIPInfoId INTEGER,
                       rcNewIPInfoExists INTEGER,
                       rcNewIPInfoPowerState INTEGER,
                       rcNewIPAddr IpAddress,
                       rcNewSubnetMask IpAddress,
                       rcNewGateway IpAddress,
                       rcNewIPConfigMethod INTEGER,
                       rcNewIPConfigEnableDisable INTEGER
                       }

           rcNewIPInfoIndex OBJECT-TYPE
                       SYNTAX  Integer32 (0..2147483647) -- was INTEGER
                       MAX-ACCESS  read-only
                       STATUS  current -- was mandatory
                       DESCRIPTION
                       "RAID Controller new IP configuration information index.
                        This MIB object is for SAS Controller Modules only.
                        NOTE: This MIB object is not applicable to modules that are running in Network Address 
                        Translation (NAT) Mode."
                       ::= { rcNewIPInfoEntry 1 }

           rcNewIPInfoId OBJECT-TYPE
                       SYNTAX  INTEGER {
                         module3(3),
                         module4(4)
                       }
                       MAX-ACCESS  read-only
                       STATUS  current -- was mandatory
                       DESCRIPTION
                       "The I/O Module numeric identifier for the RAID Controller.
                        This MIB object is for SAS Controller Modules only.
                        NOTE: This MIB object is not applicable to modules that are running in Network Address 
                        Translation (NAT) Mode."
                       ::= { rcNewIPInfoEntry 2 }

           rcNewIPInfoExists OBJECT-TYPE
                       SYNTAX  INTEGER {
                         false(0),
                         true(1)
                       }
                       MAX-ACCESS  read-only
                       STATUS  current -- was mandatory
                       DESCRIPTION
                       "Indicates whether the I/O Module exists or not.
                        This MIB object is for SAS Controller Modules only.
                        NOTE: This MIB object is not applicable to modules that are running in Network Address 
                        Translation (NAT) Mode."
                       ::= { rcNewIPInfoEntry 3 }

           rcNewIPInfoPowerState OBJECT-TYPE
                       SYNTAX  INTEGER {
                         off(0),
                         on(1),
                         shutdownInProgress(2)
                       }
                       MAX-ACCESS  read-only
                       STATUS  current -- was mandatory
                       DESCRIPTION
                       "Indicates whether the I/O Module is powered on or not.
                        This MIB object is for SAS Controller Modules only.
                        NOTE: This MIB object is not applicable to modules that are running in Network Address 
                        Translation (NAT) Mode."
                       ::= { rcNewIPInfoEntry 4 }

           rcNewIPAddr OBJECT-TYPE
                        SYNTAX  IpAddress
                        MAX-ACCESS  read-write
                        STATUS  current -- was mandatory
                        DESCRIPTION
                        "The new IP address for the RAID Controller network interface. 
                         This MIB object is for SAS Controller Modules only. Before setting this object to a new value, 
                         rcNewIpconfigEnableDisable object must first be set to disabled.
                         NOTE: This MIB object can not be set if the AMM grants the I/O Module Protected Mode 
                         permission and the module goes into Protected Mode. 
                         NOTE: This MIB object is not applicable to modules that are running in Network Address 
                         Translation (NAT) Mode."
                        ::= { rcNewIPInfoEntry 5 }


           rcNewSubnetMask OBJECT-TYPE
                        SYNTAX  IpAddress
                        MAX-ACCESS  read-write
                        STATUS  current -- was mandatory
                        DESCRIPTION
                        "The new subnet mask for the RAID Controller network interface. 
                         This MIB object is for SAS Controller Modules only. Before setting this object to a new value, 
                         rcNewIpconfigEnableDisable object must first be set to disabled.
                         NOTE: This MIB object can not be set if the AMM grants the I/O Module Protected Mode 
                         permission and the module goes into Protected Mode.
                         NOTE: This MIB object is not applicable to modules that are running in Network Address 
                         Translation (NAT) Mode."
                        ::= { rcNewIPInfoEntry 6 }

           rcNewGateway OBJECT-TYPE
                        SYNTAX  IpAddress
                        MAX-ACCESS  read-write
                        STATUS  current -- was mandatory
                        DESCRIPTION
                        "The new IP gateway for the RAID Controller network interface. 
                         This MIB object is for SAS Controller Modules only. Before setting this object to a new value, 
                         rcNewIpconfigEnableDisable object must first be set to disabled.
                         NOTE: This MIB object can not be set if the AMM grants the I/O Module Protected Mode 
                         permission and the module goes into Protected Mode.
                         NOTE: This MIB object is not applicable to modules that are running in Network Address 
                         Translation (NAT) Mode."
                        ::= { rcNewIPInfoEntry 7 }

           rcNewIPConfigMethod OBJECT-TYPE
                        SYNTAX  INTEGER {
                          unknown(0),
                          static(1),
                          dhcp(2)
                        }
                        MAX-ACCESS  read-write
                        STATUS  current -- was mandatory
                        DESCRIPTION
                        "The new IP configuration method for the RAID Controller network interface.
                         This MIB object is for SAS Controller Modules only. Before setting this object to a new value,
                         rcNewIpconfigEnableDisable object must first be set to disabled.
                         NOTE: The value 'DHCP' can not be used to set.
                         NOTE: This MIB object can not be set if the AMM grants the I/O Module Protected Mode 
                         permission and the module goes into Protected Mode.
                         NOTE: This MIB object is not applicable to modules that are running in Network Address 
                         Translation (NAT) Mode."
                        ::= { rcNewIPInfoEntry 8 }

           rcNewIPConfigEnableDisable OBJECT-TYPE
                       SYNTAX  INTEGER {
                         disable(0),
                         enable(1)
                       }
                       MAX-ACCESS  read-write
                       STATUS  current -- was mandatory
                       DESCRIPTION
                       "A set command enables new IP configurations that have been defined.
                        A get command indicates whether new IP configurations that have been enabled.
                        NOTE: This MIB object can not be set if the AMM grants the I/O Module Protected Mode 
                        permission and the module goes into Protected Mode.
                        NOTE: This MIB object is not applicable to modules that are running in Network Address 
                        Translation (NAT) Mode."
                       ::= { rcNewIPInfoEntry 11 }

    chassisTopology OBJECT IDENTIFIER ::= { blades 4 }

     chassisResponseVersion  OBJECT-TYPE
                 SYNTAX  INTEGER
                 MAX-ACCESS  read-only
                 STATUS  current -- was mandatory
                 DESCRIPTION
                 "Chassis response version."
                 ::= { chassisTopology 1 }

     chassisFlags OBJECT-TYPE
                 SYNTAX  INTEGER {
                   serverBlade(1),
                   rackOrStandAlone(0)
                 }
                 MAX-ACCESS  read-only
                 STATUS  current -- was mandatory
                 DESCRIPTION
                 "Chassis flags.
                 1 = a server blade chassis, 0 = a rack or standalone chassis."
                 ::= { chassisTopology 2 }

     chassisName OBJECT-TYPE
                 SYNTAX  OCTET STRING
                 MAX-ACCESS  read-only
                 STATUS  current -- was mandatory
                 DESCRIPTION
                 "The name of the active MM as a null terminated string."
                 ::= { chassisTopology 3 }

     chassisNoOfFPsSupported OBJECT-TYPE
                 SYNTAX  INTEGER
                 MAX-ACCESS  read-only
                 STATUS  current -- was mandatory
                 DESCRIPTION
                 "Number of fan packs (FPs) supported.

                 NOTE: Fan packs are also referred to as Power Module Cooling Devices."
                 ::= { chassisTopology 18 }

     chassisNoOfPBsSupported OBJECT-TYPE
                 SYNTAX  INTEGER
                 MAX-ACCESS  read-only
                 STATUS  current -- was mandatory
                 DESCRIPTION
                 "Number of processor blades (PBs) supported."
                 ::= { chassisTopology 19 }

     chassisNoOfSMsSupported OBJECT-TYPE
                 SYNTAX  INTEGER
                 MAX-ACCESS  read-only
                 STATUS  current -- was mandatory
                 DESCRIPTION
                 "Number of switch modules (SMs) supported."
                 ::= { chassisTopology 20 }

     chassisNoOfMMsSupported OBJECT-TYPE
                 SYNTAX  INTEGER
                 MAX-ACCESS  read-only
                 STATUS  current -- was mandatory
                 DESCRIPTION
                 "Number of management modules (MMs) supported."
                 ::= { chassisTopology 21 }

     chassisNoOfPMsSupported OBJECT-TYPE
                 SYNTAX  INTEGER
                 MAX-ACCESS  read-only
                 STATUS  current -- was mandatory
                 DESCRIPTION
                 "Number of power modules (PMs) supported."
                 ::= { chassisTopology 22 }

     chassisNoOfMTsSupported OBJECT-TYPE
                 SYNTAX  INTEGER
                 MAX-ACCESS  read-only
                 STATUS  current -- was mandatory
                 DESCRIPTION
                 "Number of media trays (MTs) supported."
                 ::= { chassisTopology 23 }

     chassisNoOfBlowersSupported OBJECT-TYPE
                 SYNTAX  INTEGER
                 MAX-ACCESS  read-only
                 STATUS  current -- was mandatory
                 DESCRIPTION
                 "Number of blowers supported.

                 NOTE: Blowers are also referred to as Chassis Cooling Devices."
                 ::= { chassisTopology 24 }

     chassisPBsInstalled OBJECT-TYPE
                 SYNTAX  OCTET STRING
                 MAX-ACCESS  read-only
                 STATUS  current -- was mandatory
                 DESCRIPTION
                 "The blades that are installed on the chassis.
                 The blades are listed as a bitmap.  The bitmap is a
                 string containing a list of 1's and 0's that is as long as
                 the number of blades supported.  If a blade is installed in a
                 bay, a 1 is present in the string in the position representing
                 the bay ID as read from left to right.  For example, if blades
                 are installed in bays 1, 5, and 13, and 14 blades are supported,
                 the string would look like '10001000000010'."
                 ::= { chassisTopology 25 }

     chassisSMsInstalled OBJECT-TYPE
                 SYNTAX  OCTET STRING
                 MAX-ACCESS  read-only
                 STATUS  current -- was mandatory
                 DESCRIPTION
                 "The switch modules that are installed on the chassis.
                 The switch modules are listed as a bitmap.  The bitmap is a
                 string containing a list of 1's and 0's that is as long as
                 the number of switch modules supported.  If a switch module is
                 installed in a bay, a 1 is present in the string in the position
                 representing the bay ID as read from left to right.  For example,
                 if switch modules are installed in bays 1 and 3, and 4 switch modules
                 are supported, the string would look like '1011' for BladeCenter and 
                 BladeCenter T and '1011000000' for BladeCenter H and BladeCenter HT."
                 ::= { chassisTopology 29 }

     chassisMMsInstalled OBJECT-TYPE
                 SYNTAX  OCTET STRING
                 MAX-ACCESS  read-only
                 STATUS  current -- was mandatory
                 DESCRIPTION
                 "The management modules that are installed on the chassis.
                 The management modules are listed as a bitmap.  The bitmap is a
                 string containing a list of 1's and 0's that is as long as the
                 number of management modules supported.  If a management module is installed
                 in a bay, a 1 is present in the string in the position representing
                 the bay ID as read from left to right.  For example, if a management module
                 is installed in bay 1, and 2 management modules are supported, the
                 string would look like '10'."
                 ::= { chassisTopology 30 }

     chassisPMsInstalled OBJECT-TYPE
                 SYNTAX  OCTET STRING
                 MAX-ACCESS  read-only
                 STATUS  current -- was mandatory
                 DESCRIPTION
                 "The power modules that are installed on the chassis.
                 The power modules are listed as a bitmap.  The bitmap is a
                 string containing a list of 1's and 0's that is as long as
                 the number of power modules supported.  If a power module is
                 installed in a bay, a 1 is present in the string in the position
                 representing the bay ID as read from left to right.  For example,
                 if power modules are installed in bays 1 and 3, and 4 power modules
                 are supported, the string would look like '1010'."
                 ::= { chassisTopology 31 }
                 
     chassisMTInstalled OBJECT-TYPE
                 SYNTAX  INTEGER {
                   no(0),
                   yes(1)
                 }
                 MAX-ACCESS  read-only
                 STATUS  current -- was mandatory
                 DESCRIPTION
                 "Indicates whether at least one media tray (MT) is installed."
                 ::= { chassisTopology 32 }


     chassisBlowersInstalled OBJECT-TYPE
                 SYNTAX  OCTET STRING
                 MAX-ACCESS  read-only
                 STATUS  current -- was mandatory
                 DESCRIPTION
                 "The blowers that are installed on the chassis.
                 The blowers are listed as a bitmap.  The bitmap is a
                 string containing a list of 1's and 0's that is as long as
                 the number of blowers supported.  If a blower is installed in a
                 bay, a 1 is present in the string in the position representing
                 the bay ID as read from left to right.  For example, if a blower
                 is installed in bay 1, and 2 blowers are supported, the string
                 would look like '10'.

                 NOTE: Blowers are also referred to as Chassis Cooling Devices."
                 ::= { chassisTopology 33 }

     chassisActiveMM OBJECT-TYPE
                 SYNTAX  INTEGER
                 MAX-ACCESS  read-only
                 STATUS  current -- was mandatory
                 DESCRIPTION
                 "The active management module (MM)."
                 ::= { chassisTopology 34 }

     chassisKVMOwner OBJECT-TYPE
                 SYNTAX  INTEGER
                 MAX-ACCESS  read-only
                 STATUS  current -- was mandatory
                 DESCRIPTION
                 "The blade that currently owns the keyboard/video/monitor (KVM).
                 0 = the KVM devices are owned by the management module."
                 ::= { chassisTopology 35 }

     chassisMediaTrayOwner OBJECT-TYPE
                 SYNTAX  INTEGER
                 MAX-ACCESS  read-only
                 STATUS  current -- was mandatory
                 DESCRIPTION
                 "The blade that currently owns the media tray.
                 0 = the media tray is owned by the management module."
                 ::= { chassisTopology 36 }

     chassisFPsInstalled OBJECT-TYPE
                 SYNTAX  OCTET STRING
                 MAX-ACCESS  read-only
                 STATUS  current -- was mandatory
                 DESCRIPTION
                 "The fan packs that are installed on the chassis.
                 The fan packs are listed as a bitmap.  The bitmap is a
                 string containing a list of 1's and 0's that is as long as
                 the number of fan packs supported.  If a fan pack is
                 installed in a bay, a 1 is present in the string in the position
                 representing the bay ID as read from left to right.  For example,
                 if fan packs are installed in bays 1 and 3, and 4 fan packs 
                 are supported, the string would look like '1010'.

                 NOTE: Fan packs are also referred to as Power Module Cooling Devices."
                 ::= { chassisTopology 37 }
      
     chassisType OBJECT-TYPE
                 SYNTAX  INTEGER {
                        bladeCenterOrBladeCenterH(97),
                        bladeCenterTOrBladeCenterHT(98)
                 }
                 MAX-ACCESS  read-only
                 STATUS  current -- was mandatory
                 DESCRIPTION
                 "The type of the chassis.  The BladeCenterS chassis and BladeCenterE are part of the
                 bladeCenterOrBladeCenterH type.  This MIB object should be used in conjunction
                 with chassisSubType MIB object to determine the characteristic of the chassis."  
                 ::= { chassisTopology 38 }
                 
     chassisSubtype OBJECT-TYPE
                 SYNTAX  INTEGER {
                        bladeCenterOrBladeCenterT(0),
                        bladeCenterHOrBladeCenterHT(2),
                        bladeCenterS(3),
                        bladeCenterE(4),
                        unknown(255)
                 }
                 MAX-ACCESS  read-only
                 STATUS  current -- was mandatory
                 DESCRIPTION
                 "The subtype of the chassis.  This MIB object should be used in conjunction with 
                 chassisType MIB object to determine the characteristic of the chassis."
                 ::= { chassisTopology 39 }
    
 -- ********************************************************************************

     chassisNoOfFBsSupported OBJECT-TYPE
                 SYNTAX  INTEGER
                 MAX-ACCESS  read-only
                 STATUS  current -- was mandatory
                 DESCRIPTION
                 "Number of Front Bezel (FBs) supported."
                 ::= { chassisTopology 40 }

     chassisNoOfAPsSupported OBJECT-TYPE
                 SYNTAX  INTEGER
                 MAX-ACCESS  read-only
                 STATUS  current -- was mandatory
                 DESCRIPTION
                 "Number of Alarm Panel (APs) supported."
                 ::= { chassisTopology 41 }

     chassisNoOfNCsSupported OBJECT-TYPE
                 SYNTAX  INTEGER
                 MAX-ACCESS  read-only
                 STATUS  current -- was mandatory
                 DESCRIPTION
                 "Number of Network Clocks (NCs) supported."
                 ::= { chassisTopology 42 }

     chassisNoOfMXsSupported OBJECT-TYPE
                 SYNTAX  INTEGER
                 MAX-ACCESS  read-only
                 STATUS  current -- was mandatory
                 DESCRIPTION
                 "Number of Multiplexer Expansion modules (MXs) supported."
                 ::= { chassisTopology 43 }

     chassisNoOfMMIsSupported OBJECT-TYPE
                 SYNTAX  INTEGER
                 MAX-ACCESS  read-only
                 STATUS  current -- was mandatory
                 DESCRIPTION
                 "Number of management module interposers (MMIs) supported."
                 ::= { chassisTopology 44 }

     chassisNoOfSMIsSupported OBJECT-TYPE
                 SYNTAX  INTEGER
                 MAX-ACCESS  read-only
                 STATUS  current -- was mandatory
                 DESCRIPTION
                 "Number of switch module interposers (SMIs) supported."
                 ::= { chassisTopology 45 }


     chassisNoOfFBsInstalled OBJECT-TYPE
                 SYNTAX  OCTET STRING
                 MAX-ACCESS  read-only
                 STATUS  current -- was mandatory
                 DESCRIPTION
                 "The return value of '1'indicates the front bezel is installed on the chassis.
                 The value of '0' indicates the front bezel is not installed."
                 ::= { chassisTopology 46 }
     
     chassisNoOfAPsInstalled OBJECT-TYPE
                 SYNTAX  OCTET STRING
                 MAX-ACCESS  read-only
                 STATUS  current -- was mandatory
                 DESCRIPTION
                 "The return value of '1'indicates the alarm panel is installed on the chassis.
                 The value of '0' indicates the alarm panel is not installed."
                 ::= { chassisTopology 47 }

     chassisNoOfNCsInstalled OBJECT-TYPE
                 SYNTAX  OCTET STRING
                 MAX-ACCESS  read-only
                 STATUS  current -- was mandatory
                 DESCRIPTION
                 "The network clock cards that are installed on the chassis.
                 The network clock cards are listed as a bitmap.  The bitmap is a
                 string containing a list of 1's and 0's that is as long as
                 the number of network clock cards supported.  If a network clock 
                 card is installed in a bay, a 1 is present in the string in the position
                 representing the bay ID as read from left to right.  For example,
                 if a network clock card is installed in bays 1, and 2 network clock cards 
                 are supported, the string would look like '10'."
                 ::= { chassisTopology 48 }

     chassisNoOfMXsInstalled OBJECT-TYPE
                 SYNTAX  OCTET STRING
                 MAX-ACCESS  read-only
                 STATUS  current -- was mandatory
                 DESCRIPTION
                 "The Multiplexer Expansion Modules that are installed on the chassis.
                 The Multiplexer Expansion Modules are listed as a bitmap.  The bitmap is a
                 string containing a list of 1's and 0's that is as long as the number of 
                 Multiplexer Expansion Modules supported.  If a Multiplexer Expansion Module 
                 is installed in a bay, a 1 is present in the string in the position
                 representing the bay ID as read from left to right.  For example,
                 if Multiplexer Expansion Module is installed in bays 1, and 2 Multiplexer 
                 Expansion Modules are supported, the string would look like '10'."
                 ::= { chassisTopology 49 }

     chassisNoOfMMIsInstalled OBJECT-TYPE
                 SYNTAX  OCTET STRING
                 MAX-ACCESS  read-only
                 STATUS  current -- was mandatory
                 DESCRIPTION
                 "The flex cables that are installed on the chassis.
                 The flex cables are listed as a bitmap.  The bitmap is a
                 string containing a list of 1's and 0's that is as long as
                 the number of flex cables supported.  If a flex cable  
                 is installed in a bay, a 1 is present in the string in the position
                 representing the bay ID as read from left to right.  For example,
                 if flex cable is installed in bays 1, and 2 flex cables are  
                 supported, the string would look like '10'."
                 ::= { chassisTopology 50 }

     chassisNoOfSMIsInstalled OBJECT-TYPE
                 SYNTAX  OCTET STRING
                 MAX-ACCESS  read-only
                 STATUS  current -- was mandatory
                 DESCRIPTION
                 "The interposers that are installed on the chassis.
                 The interposers are listed as a bitmap.  The bitmap is a
                 string containing a list of 1's and 0's that is as long as
                 the number of interposers supported.  If an interposer  
                 is installed in a bay, a 1 is present in the string in the position
                 representing the bay ID as read from left to right.  For example,
                 if interposer is installed in bays 1, and 10 interposers are  
                 supported, the string would look like '1000000000'."
                 ::= { chassisTopology 51 }

     chassisNoOfMTsInstalled OBJECT-TYPE
                 SYNTAX  OCTET STRING
                 MAX-ACCESS  read-only
                 STATUS  current -- was mandatory
                 DESCRIPTION
                 "The media trays that are installed on the chassis.
                 The media trays are listed as a bitmap.  The bitmap is a
                 string containing a list of 1's and 0's that is as long as
                 the number of media trays supported.  If a media tray is
                 installed in a bay, a 1 is present in the string in the position
                 representing the bay ID as read from left to right.  For example,
                 if media trays are installed in bays 1, and 2 media trays are, 
                 the string would look like '10'."
                 ::= { chassisTopology 52 }


 -- ********************************************************************************
    managementModule OBJECT IDENTIFIER ::= { blades 5 }
 -- ********************************************************************************

      mmStatusTable OBJECT-TYPE
                    SYNTAX  SEQUENCE OF MmStatusEntry
                    MAX-ACCESS  not-accessible
                    STATUS  current -- was mandatory
                    DESCRIPTION
                    "Table of the management module status.
                    For consistent results, view as a table and not as individual entries."
                    ::= { managementModule 1 }

      mmStatusEntry OBJECT-TYPE
                    SYNTAX MmStatusEntry
                    MAX-ACCESS  not-accessible
                    STATUS  current -- was mandatory
                    DESCRIPTION
                    "Management module status entry.
                    For consistent results, view as a table and not as individual entries."
                    INDEX { mmStatusIndex }
                    ::= { mmStatusTable 1 }

      MmStatusEntry ::= SEQUENCE {
                  mmStatusIndex INTEGER,
                  mmPresent INTEGER,
                  mmExtIpAddress IpAddress,
                  mmPrimary INTEGER,
                  mmHealthState INTEGER
                  }

      mmStatusIndex  OBJECT-TYPE
                  SYNTAX  Integer32 (0..2147483647) -- was INTEGER
                  MAX-ACCESS  read-only
                  STATUS  current -- was mandatory
                  DESCRIPTION
                  "Management module status index."
                  ::= { mmStatusEntry 1 }

      mmPresent  OBJECT-TYPE
                  SYNTAX  INTEGER {
                        no(0),
                        yes(1)
                  }
                  MAX-ACCESS  read-only
                  STATUS  current -- was mandatory
                  DESCRIPTION
                  "Management module current status."
                  ::= { mmStatusEntry 2 }

      mmExtIpAddress  OBJECT-TYPE
                  SYNTAX  IpAddress
                  MAX-ACCESS  read-only
                  STATUS  current -- was mandatory
                  DESCRIPTION
                  "Management module external IP address."
                  ::= { mmStatusEntry 3 }

      mmPrimary  OBJECT-TYPE
                  SYNTAX  INTEGER {
                        no(0),
                        yes(1)
                  }
                  MAX-ACCESS  read-only
                  STATUS  current -- was mandatory
                  DESCRIPTION
                  "Indicates if this Management module is a primary or not.
                  NOTE: If there is no standby MM, this value defaults to primary."
                  ::= { mmStatusEntry 4 }

      mmHealthState  OBJECT-TYPE
                  SYNTAX  INTEGER {
                        unknown(0),
                        good(1),
                        warning(2),
                        bad(3)                        
                  }
                  MAX-ACCESS  read-only
                  STATUS  current -- was mandatory
                  DESCRIPTION
                  "The health state for the management module. 
                   0 = unknown, 1 = good, 2 = warning, 3 = bad."
                  ::= { mmStatusEntry 5 }

    -- ********************************************************************************
    -- Storage Task for configuration
    -- ********************************************************************************
    storage OBJECT IDENTIFIER ::= { blades 6 }

      storageStatus OBJECT IDENTIFIER ::= { storage 1 }

      storageStatusTable OBJECT-TYPE
                    SYNTAX  SEQUENCE OF StorageStatusEntry
                    MAX-ACCESS  not-accessible
                    STATUS  current -- was mandatory
                    DESCRIPTION
                    "Table of the storage module status. 
                    For consistent results, view as a table and not as individual entries.

                    NOTE: This MIB object is for BCS only."
                    ::= { storageStatus 1 }
                    
         storageStatusEntry OBJECT-TYPE
                       SYNTAX  StorageStatusEntry
                       MAX-ACCESS  not-accessible
                       STATUS  current -- was mandatory
                       DESCRIPTION
                       "Storage Module Status Table Entry."
                       INDEX { storageStatusIndex }
                       ::= { storageStatusTable 1 }

         StorageStatusEntry ::= SEQUENCE {
                     storageStatusIndex INTEGER,
                     storageBayNumber OCTET STRING,
                     storageState INTEGER,
                     storageName OCTET STRING
         }

         storageStatusIndex  OBJECT-TYPE
                     SYNTAX  Integer32 (0..2147483647) -- was INTEGER
                     MAX-ACCESS  read-only
                     STATUS  current -- was mandatory
                     DESCRIPTION
                     "Storage device status table index."
                     ::= { storageStatusEntry 1 }

         storageBayNumber  OBJECT-TYPE
                     SYNTAX  OCTET STRING
                     MAX-ACCESS  read-only
                     STATUS  current -- was mandatory
                     DESCRIPTION
                     "Bay number of the Storage device."
                     ::= { storageStatusEntry 2 }

         storageState  OBJECT-TYPE
                     SYNTAX  INTEGER {
                     unknown(0),
                     good(1),
                     warning(2),
                     critical(3),
                     notAvailable(255)
                     }
                     MAX-ACCESS  read-only
                     STATUS  current -- was mandatory
                     DESCRIPTION
                     "Storage device state."
                     ::= { storageStatusEntry 3 }

         storageName OBJECT-TYPE
                     SYNTAX  OCTET STRING
                     MAX-ACCESS  read-only
                     STATUS  current -- was mandatory
                     DESCRIPTION
                     "The name of the storage device."
                     ::= { storageStatusEntry 4 }

      storageConfiguration OBJECT IDENTIFIER ::= { storage 2 }

      storageSwitchConfiguration OBJECT IDENTIFIER ::= { storageConfiguration 1 }

    -- ********************************************************************************
    -- Shows details about all possible zone configurations available on all SAS switches
    -- and allows a user to select one and make it the active zone configuration 
    -- ********************************************************************************
    
      storageSwitchZoneCfgTable OBJECT-TYPE
                    SYNTAX  SEQUENCE OF StorageSwitchZoneCfgEntry
                    MAX-ACCESS  not-accessible
                    STATUS  current -- was mandatory
                    DESCRIPTION
                    "Table of all the zone configurations stored on switch 
                    modules. For consistent results, view as a table and 
                    not as individual entries.
                    
                    Before activating a new zone configuration via the switchActiveZoneCfg
                    object, a user must consider the following:
                       
                        1) Changing the zone configuration may cause disruption in the storage
                           access of blades connected to this SAS Module. It is highly recommended
                           that you first ensure that the blades have completed all storage accesses.
                           You may want to shutdown the blade OS prior to changing your zone configuration.
                           
                        2) When selecting a zone configuration, ensure that it is appropriate 
                           for the number of SAS switches installed in your chassis. This can 
                           be determined from the switchZoneCfgDescription text.
                           
                        3) When selecting a zone configuration, ensure that it exists first on 
                           all SAS switches. This can be determined by querying the 
                           storageSwitchZoneCfgTable. In addition, for user-defined zone 
                           configurations, even if the number is the same, ensure that the 
                           actual zone configurations are identical or compatible. You will need
                           to use an application, such as the Switch Configuration Manager (SCM)
                           to verify this. 
                           
                        4) All SAS switches must be in operational state prior to activating a 
                           new zone configuration. This can be determined by querying the 
                           activeZoneCfgNumberBySwitch object and ensuring that none of the 
                           2xx codes are returned."
                    ::= { storageSwitchConfiguration 1 }
                    
         storageSwitchZoneCfgEntry OBJECT-TYPE
                       SYNTAX  StorageSwitchZoneCfgEntry
                       MAX-ACCESS  not-accessible
                       STATUS  current -- was mandatory
                       DESCRIPTION
                       "Switch Module Zone Configuration Management Entry."
                       INDEX { switchZoneCfgIndex }
                       ::= { storageSwitchZoneCfgTable 1 }

         StorageSwitchZoneCfgEntry ::= SEQUENCE {
                     switchZoneCfgIndex INTEGER,
                     switchZoneCfgBayNumber INTEGER,
                     switchZoneCfgNumber INTEGER,
                     switchZoneCfgStatus INTEGER,
                     switchZoneCfgType INTEGER,
                     switchZoneCfgName OCTET STRING,
                     switchZoneCfgDescription OCTET STRING,
                     switchZoneCfgDate OCTET STRING,
                     switchActiveZoneCfg INTEGER
         }

         switchZoneCfgIndex  OBJECT-TYPE
                     SYNTAX  Integer32 (0..2147483647) -- was INTEGER
                     MAX-ACCESS  read-only
                     STATUS  current -- was mandatory
                     DESCRIPTION
                     "Switch module zone configuration table index."
                     ::= { storageSwitchZoneCfgEntry 1 }

         switchZoneCfgBayNumber  OBJECT-TYPE
                     SYNTAX  INTEGER
                     MAX-ACCESS  read-only
                     STATUS  current -- was mandatory
                     DESCRIPTION
                     "The numeric switch bay number."
                     ::= { storageSwitchZoneCfgEntry 2 }

         switchZoneCfgNumber OBJECT-TYPE
                     SYNTAX  INTEGER
                     MAX-ACCESS  read-only
                     STATUS  current -- was mandatory
                     DESCRIPTION
                     "The zone configuration number, also referred to as the 
                     configuration store number."
                     ::= { storageSwitchZoneCfgEntry 3 }

         switchZoneCfgStatus OBJECT-TYPE
                     SYNTAX  INTEGER {
                       nonActive(0),
                       active(1),
                       pending(2)
                     }
                     MAX-ACCESS  read-only
                     STATUS  current -- was mandatory
                     DESCRIPTION
                     "The status of the zone configuration.
                     
                     Only one configuration is 'Active', others are in 'nonActive' 
                     status. 
                     
                     When a zone configuration is active on a switch, the status
                     may temporarily indicate pending(2) as it transitions from 
                     nonActive(0) to active (1)."
                     ::= { storageSwitchZoneCfgEntry 4 }

         switchZoneCfgType  OBJECT-TYPE
                   SYNTAX  INTEGER {
                     userdefined(1),
                     predefined(2)
                   }
                   MAX-ACCESS  read-only
                   STATUS  current -- was mandatory
                   DESCRIPTION
                   "The type of the zone configuration. Predefined are read-only
                   static configurations, and userdefined are read-write
                   configurations that can be created and modified using the 
                   Switch Configuration Manager application."
                   ::= { storageSwitchZoneCfgEntry 5 }

         switchZoneCfgName OBJECT-TYPE
                     SYNTAX  OCTET STRING
                     MAX-ACCESS  read-only
                     STATUS  current -- was mandatory
                     DESCRIPTION
                     "A short descriptive name for the zone configuration."
                     ::= { storageSwitchZoneCfgEntry 6 }

         switchZoneCfgDescription OBJECT-TYPE
                     SYNTAX  OCTET STRING
                     MAX-ACCESS  read-only
                     STATUS  current -- was mandatory
                     DESCRIPTION
                     "A detailed description for the zone configuration."
                     ::= { storageSwitchZoneCfgEntry 7 }

         switchZoneCfgDate OBJECT-TYPE
                     SYNTAX  OCTET STRING
                     MAX-ACCESS  read-only
                     STATUS  current -- was mandatory
                     DESCRIPTION
                     "The date the zone configuration was created."
                     ::= { storageSwitchZoneCfgEntry 8 }

         switchActiveZoneCfg OBJECT-TYPE
                     SYNTAX  INTEGER {
                       execute(1)
                     }
                     MAX-ACCESS  read-write
                     STATUS  current -- was mandatory
                     DESCRIPTION
                     "An object used to activate a particular zone configuration.
                     
                     NOTE: Value returned for the GET command is meaningless 
                           for this MIB object."
                     ::= { storageSwitchZoneCfgEntry 9 }
                     
    -- ********************************************************************************
    -- Shows which zone configuration is currently the active one on each SAS switch.
    -- ********************************************************************************
    
       storageSwitchActiveZoneCfgTable OBJECT-TYPE
                    SYNTAX  SEQUENCE OF StorageSwitchActiveZoneCfgEntry
                    MAX-ACCESS  not-accessible
                    STATUS  current -- was mandatory
                    DESCRIPTION
                    "Table showing the zone configuration that is currently  
                    active on a given switch module. For consistent results, 
                    view as a table and not as individual entries."
                    ::= { storageSwitchConfiguration 2 }
      
         storageSwitchActiveZoneCfgEntry OBJECT-TYPE
                       SYNTAX  StorageSwitchActiveZoneCfgEntry
                       MAX-ACCESS  not-accessible
                       STATUS  current -- was mandatory
                       DESCRIPTION
                       "Active zone configurations Entry."
                       INDEX { activeZoneCfgIndex }
                       ::= { storageSwitchActiveZoneCfgTable 1 }

         StorageSwitchActiveZoneCfgEntry ::= SEQUENCE {
                     activeZoneCfgIndex INTEGER,
                     activeZoneCfgBayNumber OCTET STRING,
                     activeZoneCfgNumberBySwitch INTEGER,
                     activeZoneCfgNumberByMM INTEGER
         }

         activeZoneCfgIndex  OBJECT-TYPE
                     SYNTAX  Integer32 (0..2147483647) -- was INTEGER
                     MAX-ACCESS  read-only
                     STATUS  current -- was mandatory
                     DESCRIPTION
                     "Active zone configurations table index."
                     ::= { storageSwitchActiveZoneCfgEntry 1 }

         activeZoneCfgBayNumber  OBJECT-TYPE
                     SYNTAX  OCTET STRING
                     MAX-ACCESS  read-only
                     STATUS  current -- was mandatory
                     DESCRIPTION
                     "Bay number of the switch module where active zone configurations exist."
                     ::= { storageSwitchActiveZoneCfgEntry 2 }

         activeZoneCfgNumberBySwitch OBJECT-TYPE
                     SYNTAX  INTEGER
                     MAX-ACCESS  read-only
                     STATUS  current -- was mandatory
                     DESCRIPTION
                     "The zone configuration number active on this SAS switch module
                      as reported by the switch module. If this number differs from the 
                      value of the activeZoneCfgNumberByMM object for the same 
                      switch, this may indicate a configuration problem.
                     
                      The zone configuration number is also referred to as the zone 
                      configuration store. 
                     
                     NOTE: 
                        0 = No zone configuration is active on this I/O Module.
                        253 = I/O module is discovering zone information.
                        254 = I/O Module is not powered on or in a fault state.
                        255 = notApplicable."
                     ::= { storageSwitchActiveZoneCfgEntry 3 }

         activeZoneCfgNumberByMM OBJECT-TYPE
                     SYNTAX  INTEGER
                     MAX-ACCESS  read-only
                     STATUS  current -- was mandatory
                     DESCRIPTION
                     "The zone configuration number active on this SAS switch module
                      as known by the management module. If this number differs from the 
                      value of the activeZoneCfgNumberBySwitch object for the same 
                      switch, this may indicate a configuration problem.
                     
                      The zone configuration number is also referred to as the zone 
                      configuration store. 
                     
                     NOTE: 
                        0 = No zone configuration is active on this I/O Module.
                        255 = notApplicable."
                     ::= { storageSwitchActiveZoneCfgEntry 4 }

    -- ********************************************************************************
    -- A quick means of activating the same zone configuration on all SAS switches. 
    -- ********************************************************************************
    
         switchZoneCfgActivation OBJECT-TYPE
                      SYNTAX  INTEGER 
                      MAX-ACCESS  read-write
                      STATUS  current -- was mandatory
                      DESCRIPTION
                      "This object provides a quick means of activating a valid zone 
                       configuration on all active SAS switches. The zone configuration 
                       to be activated is specified as the value of the SET and can be
                       obtained from the switchZoneCfgNumber object. 
                       
                       The zone configuration number is also referred to as the zone 
                       configuration store.
                       
                       Before activating a new zone configuration, a user must consider 
                       the following:
                       
                        1) Changing the zone configuration may cause disruption in the storage
                           access of blades connected to this SAS Module. It is highly recommended
                           that you first ensure that the blades have completed all storage accesses.
                           You may want to shutdown the blade OS prior to changing your zone configuration. 
                           
                        2) When selecting a zone configuration, ensure that it is appropriate 
                           for the number of SAS switches installed in your chassis. This can 
                           be determined from the switchZoneCfgDescription text.
                           
                        3) When selecting a zone configuration, ensure that it exists first on 
                           all SAS switches. This can be determined by querying the 
                           storageSwitchZoneCfgTable. In addition, for user-defined zone 
                           configurations, even if the number is the same, ensure that the 
                           actual zone configurations are identical or compatible. You will need
                           to use an application, such as the Switch Configuration Manager (SCM) 
                           to verify this. 
                           
                        4) All SAS switches must be in operational state prior to activating a 
                           new zone configuration. This can be determined by querying the 
                           activeZoneCfgNumberBySwitch object and ensuring that none of the 
                           2xx codes are returned.  
                      
                       NOTE: Value returned for the GET command is meaningless 
                             for this MIB object.
                            
                       If any of the switches are not activated, an error response
                       will be returned."
                      ::= { storageSwitchConfiguration 3 }
                      
    -- ********************************************************************************
    -- Firmware Image Information - currently for Iswitches that support multiple images
    -- ********************************************************************************
    firmwareInformation  OBJECT IDENTIFIER ::= { blades 8 }

      smFirmwareInformation  OBJECT IDENTIFIER ::= { firmwareInformation 1 }

          smFirmwareInfoTable OBJECT-TYPE
                      SYNTAX  SEQUENCE OF SmFirmwareInfoEntry
                      MAX-ACCESS  not-accessible
                      STATUS  current -- was mandatory
                      DESCRIPTION
                      "Switch Module firmware image information.
                      This table is only applicable to modules that support multiple images"
                      ::= { smFirmwareInformation 1 }

           smFirmwareInfoEntry  OBJECT-TYPE
                         SYNTAX SmFirmwareInfoEntry
                         MAX-ACCESS  not-accessible
                         STATUS  current -- was mandatory
                         DESCRIPTION
                         "Switch Module firmware image information table entry"
                         INDEX { smFirmwareInfoIndex }
                         ::= { smFirmwareInfoTable 1 }

           SmFirmwareInfoEntry ::= SEQUENCE {
                       smFirmwareInfoIndex INTEGER,
                       smFirmwareInfoModIndex INTEGER,
                       smFirmwareInfoImageIndex INTEGER,
                       smFirmwareInfoImageName OCTET STRING
                       }
           
           smFirmwareInfoIndex OBJECT-TYPE
                       SYNTAX  Integer32 (0..2147483647) -- was INTEGER
                       MAX-ACCESS  read-only
                       STATUS  current -- was mandatory
                       DESCRIPTION
                       "Sequence index in the firmware table."
                       ::= { smFirmwareInfoEntry 1 }

           smFirmwareInfoModIndex OBJECT-TYPE
                       SYNTAX  Integer32 (0..2147483647) -- was INTEGER
                       MAX-ACCESS  read-only
                       STATUS  current -- was mandatory
                       DESCRIPTION
                       "Switch Module number."
                       ::= { smFirmwareInfoEntry 2 }

           smFirmwareInfoImageIndex OBJECT-TYPE
                       SYNTAX  Integer32 (0..2147483647) -- was INTEGER
                       MAX-ACCESS  read-only
                       STATUS  current -- was mandatory
                       DESCRIPTION
                       "Switch Module firmware image index."
                       ::= { smFirmwareInfoEntry 3 }

           smFirmwareInfoImageName OBJECT-TYPE
                        SYNTAX  OCTET STRING
                        MAX-ACCESS  read-write
                        STATUS  current -- was mandatory
                        DESCRIPTION
                        "Switch Module firmware image name"
                        ::= { smFirmwareInfoEntry 4 }

    -- ********************************************************************************
    -- Firmware update for MM, Switch modules, and blades
    -- ********************************************************************************
    firmwareUpdate OBJECT IDENTIFIER ::= { blades 9 }
   
    firmwareUpdateTarget        OBJECT-TYPE
                                SYNTAX  INTEGER {
                                  managementModule(0), 
                                  switchModule1(11), 
                                  switchModule2(12), 
                                  switchModule3(13), 
                                  switchModule4(14), 
                                  switchModule5(15), 
                                  switchModule6(16), 
                                  switchModule7(17), 
                                  switchModule8(18), 
                                  switchModule9(19), 
                                  switchModule10(20), 
                                  blade1(31), 
                                  blade2(32), 
                                  blade3(33),
                                  blade4(34),
                                  blade5(35), 
                                  blade6(36),
                                  blade7(37), 
                                  blade8(38),
                                  blade9(39), 
                                  blade10(40),
                                  blade11(41),
                                  blade12(42),
                                  blade13(43),
                                  blade14(44), 
                                  unknown(255)
                                }  
                                MAX-ACCESS  read-write
                                STATUS  current -- was mandatory
                                DESCRIPTION
                                "Target module whose firmware will be updated.
                                NOTE: Some switch modules do not allow firmware update.  
                                When firmware update is attempted on those switch modules, 
                                the agent will report an error."
                                ::= { firmwareUpdate 1 }

    firmwareUpdateTftpServer    OBJECT-TYPE
                                SYNTAX  OCTET STRING (SIZE(0..63))
                                MAX-ACCESS  read-write
                                STATUS  current -- was mandatory
                                DESCRIPTION
                                "If flashing via the legacy method using a tftp server, then
                                set the IP address or host name of the TFTP server where
                                the firmware file resides. The address must be entered in a
                                dotted decimal IP string (e.g. 9.37.44.2)."
                                ::= { firmwareUpdate 2 }
    
    firmwareUpdateFileName      OBJECT-TYPE
                                SYNTAX  OCTET STRING (SIZE(0..254))
                                MAX-ACCESS  read-write
                                STATUS  current -- was mandatory
                                DESCRIPTION
                                "File name of the firmware file."
                                ::= { firmwareUpdate 3 }
                     
    firmwareUpdateStart         OBJECT-TYPE
                                SYNTAX INTEGER { 
                                  execute(1),
                                  execute-with-reboot(2),
                                  execute-nowait(3),
                                  execute-with-reboot-nowait(4)
                                }  
                                MAX-ACCESS  read-write
                                STATUS  current -- was mandatory
                                DESCRIPTION
                                "Start updating the firmware of the specified target module. 
                                Using execute or execute-with-reboot will cause the SNMP client to
                                wait for the firmware update to complete.
                                Using execute-nowait or execute-with-reboot-nowait will not cause 
                                the SNMP client to wait for the update to complete. Instead it will
                                flash the firmware in the background.
                                
                                Note 1: If the execute-with-reboot or execute-with-reboot-nowait
                                option is selected, the target will reset after a successful flash.  
                                This option is only valid if the firmwareUpdateTarget object is 
                                set to managementModule.
                                Note 2: If flashing from a remote file, then both
                                firmwareUpdateServer and firmwareUpdateFileName must be
                                set. Otherwise if flashing via the legacy method using a tftp
                                server, then both firmwareUpdateTftpServer and
                                firmwareUpdateFileName must be set.
                                Note 3: Depending on the target, it might take up to several 
                                minutes for the flash update to complete.  Do not reset the 
                                target until the control has been returned.  At this point, 
                                the results will be displayed. 
                                Note 4: Use firmwareUpdateStatus to confirm the status of 
                                the last firmware update initiated by SNMP method.  The 
                                Management Module must be restarted for the new firmware to 
                                take affect.
                                Note 5: If data encryption is currently enabled on this MM, 
                                and you update the MM firmware to a level which does not
                                support data encryption, you will lose all your configuration 
                                settings as a result.
                                Note 6: Since some I/O Module types use the AMM TFTP server for 
                                firmware file transfer during the firmware update process, the  
                                tftpEnable MIB object must be set to enable prior to updating 
                                the firmware for these modules.
                                
                                NOTE: Value returned for the GET command is meaningless 
                                for this MIB object."
                                ::= { firmwareUpdate 4 }

    firmwareUpdateStatus        OBJECT-TYPE
                                SYNTAX OCTET STRING 
                                MAX-ACCESS  read-only
                                STATUS  current -- was mandatory
                                DESCRIPTION
                                "Get the status of the last firmware update which was 
                                initiated through SNMP method."
                                ::= { firmwareUpdate 5 }

    standbyFirmwareUpdateStatus  OBJECT-TYPE
                                 SYNTAX OCTET STRING 
                                 MAX-ACCESS  read-only
                                 STATUS  current -- was mandatory
                                 DESCRIPTION
                                 "Get the current status of the firmware update for the standby AMM.

                                 NOTE: This only applies to systems with a standby AMM."
                                 ::= { firmwareUpdate 6 }
 
    firmwareImageNumber          OBJECT-TYPE
                                 SYNTAX INTEGER
                                 MAX-ACCESS  read-write
                                 STATUS  current -- was mandatory
                                 DESCRIPTION
                                 "If the module can upload more than one image, an image
                                 number must be specified after setting the firmware target.
                                 Please refer to the firmwareInformation section."
                                 ::= { firmwareUpdate 7 }

    firmwareActiveImage          OBJECT-TYPE
                                 SYNTAX INTEGER
                                 MAX-ACCESS  read-write
                                 STATUS  current -- was mandatory
                                 DESCRIPTION
                                 "If the module can upload more than one image, an active image
                                 number must be specified.  Please refer to the firmwareInformation section.
                                 NOTE: Value returned for the GET command is meaningless for this 
                                 MIB object."
                                 ::= { firmwareUpdate 8 }

    firmwareUpdateServer         OBJECT-TYPE
                                 SYNTAX OCTET STRING (SIZE(0..254))
                                 MAX-ACCESS  read-write
                                 STATUS  current -- was mandatory
                                 DESCRIPTION
                                 "Contains the fully qualified remote location of the firmware
                                 packet file. Use firmwareUpdateFileName to specify the filename.
                          
                                 A fully qualified remote location contains a supported
                                 protocol followed by a colon and two slashes (//), userid and
                                 password separated by a colon for login authentication, an
                                 @ sign, followed by the hostname or IP address of the
                                 server where the packet file resides, followed by an optional
                                 port number to the hostname, and the full pathname to the file. 
                                 Note that if the port number is specified, it must be
                                 separated with the hostname (or IP address) by a colon.

                                 The AMM currently supports the following protocols:
                                 TFTP, FTP, FTPS, HTTP and HTTPS.

                                 The complete format of a fully qualified remote location is:

                                 <protocol>://<userid:password>@<hostname:port>/<pathname>
                                                   
                                 An example of a fully qualified remote location can be:
                                       ftp://USERID:PASSW0RD@192.168.0.2:30045/tmp
                                 where the ftp protocol will be used for transferring the file in
                                 this location, username is USERID,  password is
                                 PASSW0RD, host IP address is 192.168.0.2, port number is
                                 30045, and the full pathname for the packet file is /tmp.

                                 and firmwareUpdateFileName is set to: CNETCMUS.pkt

                                 Some protocols do not need the username, password, and
                                 the port number, so the minimum requirement for a fully
                                 qualified location can be:  <protocol>://<hostname>/<pathname>."
                                 ::= { firmwareUpdate 9 }

    -- ********************************************************************************
    -- mm Discovery
    -- ********************************************************************************
      remoteChassis OBJECT IDENTIFIER ::= { blades 10 }

      remoteChassisTable OBJECT-TYPE
                     SYNTAX  SEQUENCE OF RemoteChassisEntry
                     MAX-ACCESS  not-accessible
                     STATUS  current -- was mandatory
                     DESCRIPTION
                     "Table of remote chassis information."
                     ::= { remoteChassis 1 }  

       remoteChassisEntry OBJECT-TYPE
                     SYNTAX RemoteChassisEntry
                     MAX-ACCESS  not-accessible
                     STATUS  current -- was mandatory
                     DESCRIPTION
                     "Remote chassis entry"
                     INDEX { remoteChassisIndex }
                     ::= { remoteChassisTable 1 }   

       RemoteChassisEntry ::= SEQUENCE {
                   remoteChassisIndex INTEGER,
                   systemName OCTET STRING,
                   systemStatus   INTEGER,                   
                   mmType  OCTET STRING,
                   mmSerial OCTET STRING,
                   mmFru   OCTET STRING,
                   mmIp    OCTET STRING,                   
                   chassisSerial OCTET STRING,
                   chassisFru   OCTET STRING,
                   chassisMachineTypeMode OCTET STRING,
                   chassisUuid OCTET STRING,
                   firmwareVersion OCTET STRING
                   }

       
      remoteChassisIndex  OBJECT-TYPE
                   SYNTAX  Integer32 (0..2147483647) -- was INTEGER
                   MAX-ACCESS  read-only
                   STATUS  current -- was mandatory
                   DESCRIPTION
                   "Remote chassis discovery sequence index."
                   ::= { remoteChassisEntry 1 }

      systemName OBJECT-TYPE
                   SYNTAX  OCTET STRING 
                   MAX-ACCESS  read-only
                   STATUS  current -- was mandatory
                   DESCRIPTION
                   "System name for this discovery management module."
                   ::= { remoteChassisEntry 2 }

      systemStatus OBJECT-TYPE
                   SYNTAX  INTEGER {
                        critical(0),
                        non-Critical(2),
                        system-Level(4),
                        unknown(9),
                        noResponse(170),
                        normal(255)
                   }
                   MAX-ACCESS  read-only
                   STATUS  current -- was mandatory
                   DESCRIPTION
                   "System status summary (chassis)."
                   ::= { remoteChassisEntry 3 }

      mmType       OBJECT-TYPE
                   SYNTAX  OCTET STRING 
                   MAX-ACCESS  read-only
                   STATUS  current -- was mandatory
                   DESCRIPTION
                   "Service processor type."
                   ::= { remoteChassisEntry 4 }

      mmSerial     OBJECT-TYPE
                   SYNTAX  OCTET STRING 
                   MAX-ACCESS  read-only
                   STATUS  current -- was mandatory
                   DESCRIPTION
                   "Management module serial number."
                   ::= { remoteChassisEntry 5 }  

      mmFru        OBJECT-TYPE
                   SYNTAX  OCTET STRING 
                   MAX-ACCESS  read-only
                   STATUS  current -- was mandatory
                   DESCRIPTION
                   "Management module Field-Replaceable number."
                   ::= { remoteChassisEntry 6 } 

      mmIp            OBJECT-TYPE
                      SYNTAX  OCTET STRING 
                      MAX-ACCESS  read-write
                      STATUS  current -- was mandatory
                      DESCRIPTION
                      "The IPv4 compliant address of the management module."
                      ::= { remoteChassisEntry 7}
                     
                   
      chassisSerial OBJECT-TYPE
                   SYNTAX  OCTET STRING 
                   MAX-ACCESS  read-only
                   STATUS  current -- was mandatory
                   DESCRIPTION
                   "Chassis serial number."
                   ::= { remoteChassisEntry 8 }

      chassisFru OBJECT-TYPE
                   SYNTAX  OCTET STRING 
                   MAX-ACCESS  read-only
                   STATUS  current -- was mandatory
                   DESCRIPTION
                   "Chassis Field-Replaceable number."
                   ::= { remoteChassisEntry 9 }   

       chassisMachineTypeMode OBJECT-TYPE
                   SYNTAX  OCTET STRING 
                   MAX-ACCESS  read-only
                   STATUS  current -- was mandatory
                   DESCRIPTION
                   "Chassis machine type and model number."
                   ::= { remoteChassisEntry 10 }

       chassisUuid OBJECT-TYPE
                   SYNTAX  OCTET STRING 
                   MAX-ACCESS  read-only
                   STATUS  current -- was mandatory
                   DESCRIPTION
                   "Chassis unique identifier."
                   ::= { remoteChassisEntry 11 } 


        firmwareVersion OBJECT-TYPE
                   SYNTAX  OCTET STRING 
                   MAX-ACCESS  read-only
                   STATUS  current -- was mandatory
                   DESCRIPTION
                   "Firmware version of the discovery management module."
                   ::= { remoteChassisEntry 12 } 

        chassisDiscovery OBJECT-TYPE
                    SYNTAX INTEGER{
                       execute(1)
                    }
                    MAX-ACCESS read-write
                    STATUS current -- was mandatory
                    DESCRIPTION
                    "Discovery of remote Chassis.
                    NOTE: Value returned for the GET command is meaningless for this MIB object."
                    ::= { remoteChassis 2}

    -- ********************************************************************************
    -- Local file management
    -- ********************************************************************************    
      fileManagement OBJECT IDENTIFIER ::= { blades 11 }

       fileTopology OBJECT IDENTIFIER ::= { fileManagement 1 }
    
       currentDirectory OBJECT-TYPE
                  SYNTAX  OCTET STRING 
                  MAX-ACCESS  read-write
                  STATUS  current -- was mandatory
                  DESCRIPTION
                  "Specifies the directory name for listing the requested files."
                  ::= { fileTopology 1 }
                    
       fileDetailsTable OBJECT-TYPE
                    SYNTAX  SEQUENCE OF FileDetailsEntry
                    MAX-ACCESS  not-accessible
                    STATUS  current -- was mandatory
                    DESCRIPTION
                    "A table of all the files in the specified directory.
                    For consistent results, view as a table and not as individual entries."
                    ::= { fileTopology 2 }

       fileDetailsEntry OBJECT-TYPE
                    SYNTAX FileDetailsEntry
                    MAX-ACCESS  not-accessible
                    STATUS  current -- was mandatory
                    DESCRIPTION
                    "File details entry.
                    For consistent results, view as a table and not as individual entries."
                    INDEX { fileIndex }
                    ::= { fileDetailsTable 1 }

       FileDetailsEntry ::= SEQUENCE {
                   fileIndex INTEGER,
                   fileName OCTET STRING,
                   fileLastUpdate OCTET STRING,
                   fileSize OCTET STRING
                   }
                  
       fileIndex  OBJECT-TYPE
                  SYNTAX  Integer32 (0..2147483647) -- was INTEGER
                  MAX-ACCESS  read-only
                  STATUS  current -- was mandatory
                  DESCRIPTION
                  "File sequence index."
                  ::= { fileDetailsEntry 1 }

       fileName  OBJECT-TYPE
                  SYNTAX  OCTET STRING
                  MAX-ACCESS  read-only
                  STATUS  current -- was mandatory
                  DESCRIPTION
                  "File name."
                  ::= { fileDetailsEntry 2 }

       fileLastUpdate  OBJECT-TYPE
                  SYNTAX  OCTET STRING
                  MAX-ACCESS  read-only
                  STATUS  current -- was mandatory
                  DESCRIPTION
                  "Date of the latest file update."
                  ::= { fileDetailsEntry 3 }

       fileSize  OBJECT-TYPE
                  SYNTAX  OCTET STRING
                  MAX-ACCESS  read-only
                  STATUS  current -- was mandatory
                  DESCRIPTION
                  "File size in bytes."
                  ::= { fileDetailsEntry 4 }
      
       fileManagementCmd OBJECT-TYPE
                  SYNTAX  OCTET STRING 
                  MAX-ACCESS  read-write
                  STATUS  current -- was mandatory
                  DESCRIPTION
                  "This field will execute the selected operations on the files.
                   The following operation is supported:
                   DEL name     -   delete a file
                                                      
                   Examples:
                    - to delete the file named switch.config in tftproot directory
                    set the value to 'DEL tftproot/switch.config'

                  NOTE: Value returned for the GET command is meaningless for this 
                  MIB object."
                  ::= { fileManagement 3 }           
                                    
       fileSystemSpaceAvailable OBJECT-TYPE
                  SYNTAX  OCTET STRING 
                  MAX-ACCESS  read-only
                  STATUS  current -- was mandatory
                  DESCRIPTION
                  "This field displays the available space of the AMM file system."
                  ::= { fileManagement 6 }

    -- ************************************************************************
    -- FFDC Service
    -- ************************************************************************

    serviceConfig  OBJECT IDENTIFIER ::= { service 1 }

    debugEnable    OBJECT-TYPE
                   SYNTAX  INTEGER {
                       disabled(0),
                       enabled(1)
                   }
                   MAX-ACCESS  read-write
                   STATUS  current -- was mandatory
                   DESCRIPTION
                   "Disable/Enable AMM debugging with USB key by service personnel."
                   ::= { serviceConfig 3 }

    bladeServiceData  OBJECT IDENTIFIER ::= { service 3 }
    bladeServiceDataTable OBJECT-TYPE
                     SYNTAX  SEQUENCE OF BladeServiceDataEntry
                     MAX-ACCESS  not-accessible
                     STATUS  current -- was mandatory
                     DESCRIPTION
                     "Table of blade service data information."
                     ::= { bladeServiceData 1 }

       bladeServiceDataEntry OBJECT-TYPE
                     SYNTAX BladeServiceDataEntry
                     MAX-ACCESS  not-accessible
                     STATUS  current -- was mandatory
                     DESCRIPTION
                     "Blade service data entry"
                     INDEX { serviceDataIndex }
                     ::= { bladeServiceDataTable 1 }


       BladeServiceDataEntry ::= SEQUENCE {
                   serviceDataIndex INTEGER,
                   serviceDataBladeId INTEGER,
                   serviceDataBladeExists INTEGER,
                   serviceDataBladePowerState INTEGER,
                   serviceDataBladeName OCTET STRING,
                   serviceDataBladeCapability INTEGER,
                   serviceDataDumpInitiate INTEGER
                   }

       serviceDataIndex  OBJECT-TYPE
                   SYNTAX  Integer32 (0..2147483647) -- was INTEGER
                   MAX-ACCESS  read-only
                   STATUS  current -- was mandatory
                   DESCRIPTION
                   "Blade service date index."
                   ::= { bladeServiceDataEntry 1 }

       serviceDataBladeId   OBJECT-TYPE
                   SYNTAX  INTEGER {
                       blade1(1),
                       blade2(2),
                       blade3(3),
                       blade4(4),
                       blade5(5),
                       blade6(6),
                       blade7(7),
                       blade8(8),
                       blade9(9),
                       blade10(10),
                       blade11(11),
                       blade12(12),
                       blade13(13),
                       blade14(14)
                     }
                   MAX-ACCESS  read-only
                   STATUS  current -- was mandatory
                   DESCRIPTION
                   "The numeric blade ID."
                   ::= { bladeServiceDataEntry 2 }

       serviceDataBladeExists OBJECT-TYPE
                   SYNTAX  INTEGER {
                     false(0),
                     true(1)
                   }
                   MAX-ACCESS  read-only
                   STATUS  current -- was mandatory
                   DESCRIPTION
                   "Indicates whether the blade specified exists or not."
                   ::= { bladeServiceDataEntry 3 }

       serviceDataBladePowerState OBJECT-TYPE
                   SYNTAX  INTEGER {
                     off(0),
                     on(1)
                   }
                   MAX-ACCESS  read-only
                   STATUS  current -- was mandatory
                   DESCRIPTION
                   "Indicates whether the blade specified is powered on or not."
                   ::= { bladeServiceDataEntry 4 }

       serviceDataBladeName OBJECT-TYPE
                   SYNTAX  OCTET STRING
                   MAX-ACCESS  read-only
                   STATUS  current -- was mandatory
                   DESCRIPTION
                   "The name of the blade as a string."
                   ::= { bladeServiceDataEntry 5 }

       serviceDataBladeCapability OBJECT-TYPE
                   SYNTAX  INTEGER
                   MAX-ACCESS  read-only
                   STATUS  current -- was mandatory
                   DESCRIPTION
                   "Indicates whether the blade has the capability to trigger service data."
                   ::= { bladeServiceDataEntry 6 }

       serviceDataDumpInitiate OBJECT-TYPE
                   SYNTAX  INTEGER {
                     processorDump(1),
                     platformDump(2),
                     partitionDump(3)
                   }
                   MAX-ACCESS  read-write
                   STATUS  current -- was mandatory
                   DESCRIPTION
                   "Initiates a type of dump collection to be initiated for the blade.

                   NOTE: Value returned for the GET command is meaningless
                   for this MIB object."
                   ::= { bladeServiceDataEntry 7 }


      bladeSystemReferenceCodes  OBJECT IDENTIFIER ::= { bladeServiceData 3 }
      bladeSysRefCodesTable OBJECT-TYPE
                     SYNTAX  SEQUENCE OF BladeSysRefCodesEntry
                     MAX-ACCESS  not-accessible
                     STATUS  current -- was mandatory
                     DESCRIPTION
                     "Table of blade system reference codes."
                     ::= { bladeSystemReferenceCodes 1 }

       bladeSysRefCodesEntry OBJECT-TYPE
                     SYNTAX BladeSysRefCodesEntry
                     MAX-ACCESS  not-accessible
                     STATUS  current -- was mandatory
                     DESCRIPTION
                     "Boot sequence entry"
                     INDEX { sysRefCodeIndex }
                     ::= { bladeSysRefCodesTable 1 }

       BladeSysRefCodesEntry ::= SEQUENCE {
                   sysRefCodeIndex INTEGER,
                   sysRefCodeBayNumber OCTET STRING,
                   sysRefCodeSequence INTEGER,
                   sysRefCode OCTET STRING,
                   sysRefCodeTimestamp OCTET STRING
                   }

       sysRefCodeIndex  OBJECT-TYPE
                   SYNTAX  Integer32 (0..2147483647) -- was INTEGER
                   MAX-ACCESS  read-only
                   STATUS  current -- was mandatory
                   DESCRIPTION
                   "System reference codes index."
                   ::= { bladeSysRefCodesEntry 1 }

       sysRefCodeBayNumber   OBJECT-TYPE
                   SYNTAX  OCTET STRING
                   MAX-ACCESS  read-only
                   STATUS  current -- was mandatory
                   DESCRIPTION
                   "The bay number of the blade which has the system reference code."
                   ::= { bladeSysRefCodesEntry 2 }

       sysRefCodeSequence  OBJECT-TYPE
                   SYNTAX  INTEGER
                   MAX-ACCESS  read-only
                   STATUS  current -- was mandatory
                   DESCRIPTION
                   "Indicates whether the blade specified exists or not."
                   ::= { bladeSysRefCodesEntry 3 }

       sysRefCode  OBJECT-TYPE
                   SYNTAX  OCTET STRING
                   MAX-ACCESS  read-write
                   STATUS  current -- was mandatory
                   DESCRIPTION
                   "Unique ID and system reference code for the blade."
                   ::= { bladeSysRefCodesEntry 4 }

       sysRefCodeTimestamp  OBJECT-TYPE
                   SYNTAX  OCTET STRING
                   MAX-ACCESS  read-write
                   STATUS  current -- was mandatory
                   DESCRIPTION
                   "Timestamp of system reference code for the blade."
                   ::= { bladeSysRefCodesEntry 5 } 

      bladeSysRefCodesDetailsTable OBJECT-TYPE
                     SYNTAX  SEQUENCE OF BladeSysRefCodesDetailsEntry
                     MAX-ACCESS  not-accessible
                     STATUS  current -- was mandatory
                     DESCRIPTION
                     "Table of details of blade system reference codes."
                     ::= { bladeSystemReferenceCodes 2 }

       bladeSysRefCodesDetailsEntry OBJECT-TYPE
                     SYNTAX BladeSysRefCodesDetailsEntry
                     MAX-ACCESS  not-accessible
                     STATUS  current -- was mandatory
                     DESCRIPTION
                     "Boot sequence entry"
                     INDEX { sysRefCodeDetailIndex }
                     ::= { bladeSysRefCodesDetailsTable 1 }

       BladeSysRefCodesDetailsEntry ::= SEQUENCE {
                   sysRefCodeDetailIndex INTEGER,
                   sysRefCodeDetailBayNumber OCTET STRING,
                   sysRefCodeDetailSRCSequence INTEGER,
                   sysRefCodeDetailSequence OCTET STRING,
                   sysRefCodeDetailDataString OCTET STRING
                   }

       sysRefCodeDetailIndex  OBJECT-TYPE
                   SYNTAX  Integer32 (0..2147483647) -- was INTEGER
                   MAX-ACCESS  read-only
                   STATUS  current -- was mandatory
                   DESCRIPTION
                   "System reference codes index."
                   ::= { bladeSysRefCodesDetailsEntry 1 }

       sysRefCodeDetailBayNumber   OBJECT-TYPE
                   SYNTAX  OCTET STRING
                   MAX-ACCESS  read-only
                   STATUS  current -- was mandatory
                   DESCRIPTION
                   "The bay number of the blade which has the details
                   of system reference code."
                   ::= { bladeSysRefCodesDetailsEntry 2 }

       sysRefCodeDetailSRCSequence OBJECT-TYPE
                   SYNTAX  INTEGER 
                   MAX-ACCESS  read-only
                   STATUS  current -- was mandatory
                   DESCRIPTION
                   "A sequence of the system reference codes for the blade."
                   ::= { bladeSysRefCodesDetailsEntry 3 }

               
       sysRefCodeDetailSequence OBJECT-TYPE
                   SYNTAX  OCTET STRING
                   MAX-ACCESS  read-write
                   STATUS  current -- was mandatory
                   DESCRIPTION
                   "A sequence of the detailed information of the system reference
                   codes for the blade."
                   ::= { bladeSysRefCodesDetailsEntry 4 }

       sysRefCodeDetailDataString OBJECT-TYPE
                   SYNTAX  OCTET STRING
                   MAX-ACCESS  read-write
                   STATUS  current -- was mandatory
                   DESCRIPTION
                   "Detailed information of the system reference codes for the blade."
                   ::= { bladeSysRefCodesDetailsEntry 5 }

serviceAdvisor   OBJECT IDENTIFIER ::= { service 4 }
 
 autoCallHomeSetup   OBJECT IDENTIFIER ::= { serviceAdvisor 1 }
 
     acceptLicenseAgreement OBJECT-TYPE
         SYNTAX INTEGER {
             disabled(0),
             enabled(1)
         }
         MAX-ACCESS read-write
         STATUS current -- was mandatory
         DESCRIPTION
         "Accept Terms and Conditions of AMM Service Advisor. The user will have to accept the terms and conditions
         before Service Advisor can send diagnostic data to IBM support personnel. If AMM configuration
         is reset to defaults, the user will have to accept the terms and conditions again before they can 
         enable Service Advisor. For more information, please refer to the IBM BladeCenter User's Guide."
         ::= {autoCallHomeSetup 1}

     serviceAdvisorEnable OBJECT-TYPE
         SYNTAX INTEGER {
             disabled(0),
             enabled(1)
         }
         MAX-ACCESS read-write
         STATUS current -- was mandatory
         DESCRIPTION
         "Disable/Enable Service Advisor. The User Agreement must be accepted and the contact information 
         must be set before the Service Advisor can be enabled."
         ::= {autoCallHomeSetup 2}

serviceSupportCenter  OBJECT IDENTIFIER ::= {serviceAdvisor 2}
     ibmSupportCenter OBJECT-TYPE
         SYNTAX OCTET STRING 
         MAX-ACCESS read-write
         STATUS current -- was mandatory
         DESCRIPTION
         "The country code for the IBM Support Center. 2 character ISO country code."
         ::= {serviceSupportCenter 1}   
contactInformation  OBJECT IDENTIFIER ::= {serviceAdvisor 3}

     companyName OBJECT-TYPE
         SYNTAX OCTET STRING 
         MAX-ACCESS read-write
         STATUS current -- was mandatory
         DESCRIPTION
         " The organization/company name of the contact person. 1-30 characters."
         ::= {contactInformation 1}

     contactName OBJECT-TYPE
         SYNTAX OCTET STRING 
         MAX-ACCESS read-write
         STATUS current -- was mandatory
         DESCRIPTION
         "The name of the contact person.1-30 characters."
         ::= {contactInformation 2}

     phoneNumber OBJECT-TYPE
         SYNTAX OCTET STRING 
         MAX-ACCESS read-write
         STATUS current -- was mandatory
         DESCRIPTION
         "The phone of the contact person. 5-30 characters."
         ::= {contactInformation 3}

     emailAddress OBJECT-TYPE
         SYNTAX OCTET STRING 
         MAX-ACCESS read-write
         STATUS current -- was mandatory
         DESCRIPTION
         "The email of the contact person. It must contain '@' and dot '.' in form userid@hostname (30 characters maximum). 
         The userid can be alphanumeric characters, '.', '-', or '_' but must begin and end with alphanumeric characters. 
         The hostname can be alphanumeric characters, '.', '-', or '_'. It must contain at least two domain items. 
         Every domain item should begin and end with alphanumeric character, and the last domain item should be 2-20 alphabetic characters."
         ::= {contactInformation 4}     

     address OBJECT-TYPE
         SYNTAX OCTET STRING 
         MAX-ACCESS read-write
         STATUS current -- was mandatory
         DESCRIPTION
         "The address of the machine location. The information in this field should be of sufficient detail to allow someone to 
          quickly find the chassis when necessary. 1-30 characters."
         ::= {contactInformation 5}

     city OBJECT-TYPE
         SYNTAX OCTET STRING 
         MAX-ACCESS read-write
         STATUS current -- was mandatory
         DESCRIPTION
         "The city of the machine location. 1-30 characters."
         ::= {contactInformation 6}
         
     state OBJECT-TYPE
         SYNTAX OCTET STRING 
         MAX-ACCESS read-write
         STATUS current -- was mandatory
         DESCRIPTION
         "The state of the machine location. 2-3 characters."
         ::= {contactInformation 7}
         

         
     postalCode OBJECT-TYPE
         SYNTAX OCTET STRING 
         MAX-ACCESS read-write
         STATUS current -- was mandatory
         DESCRIPTION
         "The postal code of the location for this system. 1-9 characters, only alphanumeric characters are valid."
         ::= {contactInformation 8}
     
httpProxyConfig  OBJECT IDENTIFIER ::= {serviceAdvisor 4}

    httpProxyEnable OBJECT-TYPE
        SYNTAX INTEGER{
           disabled(0),
           enabled(1)
        }
        MAX-ACCESS read-write
        STATUS current -- was mandatory
        DESCRIPTION
        "Disable/Enable of the HTTP Proxy. Select Enable to use the proxy for call home
         connections from the AMM to IBM. HTTP Proxy is used by the AMM when it is not connected to the internet directly."
        ::= {httpProxyConfig 1}

    httpProxyLocation OBJECT-TYPE
        SYNTAX OCTET STRING 
        MAX-ACCESS read-write
        STATUS current -- was mandatory
        DESCRIPTION
        "Fully qualified host name or IP address of the HTTP Proxy. Maximum of 63 characters."
        ::= {httpProxyConfig 2}    

    httpProxyPort OBJECT-TYPE
        SYNTAX INTEGER
        MAX-ACCESS read-write
        STATUS current -- was mandatory
        DESCRIPTION
        "The port number of the HTTP Proxy. An integer value from 1 to 65535."
        ::= {httpProxyConfig 3}    

    httpProxyUserName OBJECT-TYPE
        SYNTAX OCTET STRING 
        MAX-ACCESS read-write
        STATUS current -- was mandatory
        DESCRIPTION
        "User Name of the HTTP Proxy. A maximum of 30 characters string without spaces."
        ::= {httpProxyConfig 4}    

    httpProxyPassword OBJECT-TYPE
        SYNTAX OCTET STRING 
        MAX-ACCESS read-write
        STATUS current -- was mandatory
        DESCRIPTION
        "Password of the HTTP Proxy. A maximum of 15 characters string without spaces."
        ::= {httpProxyConfig 5}    

   activityLogs   OBJECT IDENTIFIER ::= { serviceAdvisor 5}
                                        

    activityLogTable  OBJECT-TYPE
                      SYNTAX  SEQUENCE OF ActivityLogEntry
                      MAX-ACCESS  not-accessible
                     STATUS  current -- was mandatory
                      DESCRIPTION
                      "Table of Service Advisor Activity Log entries information. This table displays the last five
                      events that were generated by the system or user that are called home. The entries are displayed in 
                      reverse chronological order (most recent call home entry first). For any events that happen with same 
                      Date/Time, only one event will be called home. If a call home event that is already in the activity 
                      log is triggered again on the same event source, it will not be called home again unless the prior entry has 
                      been acknowledged as corrected or 120 hours (5 days) have passed since it initially occurred and was called home. "
                     ::= { activityLogs 1 }

      activityLogEntry OBJECT-TYPE
                    SYNTAX   ActivityLogEntry
                    MAX-ACCESS  not-accessible
                    STATUS  current -- was mandatory
                    DESCRIPTION
                    "Service Advisor Activity Log table entry. Each entry has the result of the call-home attempt, 
                    the service number assigned for the issue by IBM support, the event ID, event source, date and
                    time that event occured, and a text message."
                    INDEX { activityLogIndex }
                    ::= { activityLogTable 1 }


      ActivityLogEntry ::= SEQUENCE {
                 activityLogIndex INTEGER,
                 activityLogString OCTET STRING,
                 activityLogAcknowledge INTEGER
                  }


      activityLogIndex  OBJECT-TYPE
                  SYNTAX  Integer32 (0..2147483647) -- was INTEGER
                  MAX-ACCESS  read-only
                  STATUS  current -- was mandatory
                  DESCRIPTION
                  "The Service Advisor Activity Log index number.  
                  For consistent results, view as a table and not as individual entries."
                  ::= { activityLogEntry 1 }

      activityLogString OBJECT-TYPE
                  SYNTAX  OCTET STRING
                  MAX-ACCESS  read-only
                  STATUS  current -- was mandatory
                  DESCRIPTION
                  "A string of data detailing one Service Advisor Activity Log entry. Status PENDING indicates that the system 
                  is preparing for the event to be called home by collecting data about the systems state. A SUCCESS state 
                  indicates that the problem was successfully transmitted to IBM support. The FAILED state indicates that the attempt 
                  to transmit the event information was not successful. Additional information may be found in the Event Log. 
                  The service number is similar to a ticket number that can be used as a reference to the issue reported by the machine 
                  when contacting IBM support. The event ID, event source , date and time, and text message are all information from 
                  the original entry in the event log. 
                  The acknowledged as corrected field is a reminder to certain events to indicate their awareness of the issue. 
                  
                  For consistent results, view as a table and not as individual entries."
                  ::= { activityLogEntry 2 }

     activityLogAcknowledge OBJECT-TYPE
                  SYNTAX INTEGER{
                    no(0),
                    yes(1) }
                  MAX-ACCESS  read-write
                  STATUS  current -- was mandatory
                  DESCRIPTION
                  "The acknowledgement of one Service Advisor Activity Log entry as corrected. This field allows the users to set a reminder next to 
                  certain events to indicate their awareness of the issue. Checking the acknowledge flag will not cause the event to be removed 
                  from the log or close the ticket at IBM support. This log is not cleared, so the acknowledge flag can be used to indicate a problem 
                  can be ignored. This field can be also used to override the 120 hour (5 day) filtering of reports via Automated FTP/TFTP Problem
                  Report of Service Data.
                  For consistent results, view as a table and not as individual entries."
                  ::= { activityLogEntry 3 }
     -- ********************************************************************************
     -- autoftp
     -- ********************************************************************************
     --
       autoFTPSetup  OBJECT IDENTIFIER ::= { service 5 }
            
        autoFTPCallMode    OBJECT-TYPE
                      SYNTAX  INTEGER {
                        disabled(0),
                        ftp(1),
                        tftp(2)
                      }
                      MAX-ACCESS  read-write
                      STATUS  current -- was mandatory
                      DESCRIPTION
                      "This field specifies the automated problem reporting mode. Automated problem reporting mode allows the AMM to automatically put 
                      service data to a specified server when a call home event is detected. For any call home events that happen with same Date/Time, 
                      only one event will be reported. The system will also wait for an interval of 120 hours (5 days) before another identical event
                      can be sent for the same failed component."
                      ::= { autoFTPSetup 1 }
                      
          autoFTPCallAddr  OBJECT-TYPE
                      SYNTAX  OCTET STRING 
                      MAX-ACCESS  read-write
                      STATUS  current -- was mandatory
                      DESCRIPTION
                      "This field specifies the remote server address of FTP and TFTP. It should be fully qualified hostname or IP address."
                       ::= { autoFTPSetup 2 }
         autoFTPCallPort  OBJECT-TYPE  
                        SYNTAX  INTEGER 
                        MAX-ACCESS  read-write
                        STATUS  current -- was mandatory
                        DESCRIPTION
                        "This field specifies the port on remote FTP/TFTP server for data transmission."
                       ::= { autoFTPSetup 3 }

         autoFTPCallUserID  OBJECT-TYPE
                      SYNTAX  OCTET STRING 
                      MAX-ACCESS  read-write
                      STATUS  current -- was mandatory
                      DESCRIPTION
                      "This field specifies the user account to login remote FTP server."
                       ::= { autoFTPSetup 4 }
           
          autoFTPCallPassword   OBJECT-TYPE
                      SYNTAX  OCTET STRING 
                      MAX-ACCESS  read-write
                      STATUS  current -- was mandatory
                      DESCRIPTION
                      "This field specifies the password to login remote FTP server."
                       ::= { autoFTPSetup 5 }

-- ********************************************************************************
--    Call Home Exclusion List   
-- ********************************************************************************

callHomeExclusionEvents OBJECT IDENTIFIER ::= {  service 6}
                                        

    readCallHomeExclusionEventTable  OBJECT-TYPE
                      SYNTAX  SEQUENCE OF ReadCallHomeExclusionEventEntry 
                      MAX-ACCESS  not-accessible
                      STATUS  current -- was mandatory
                      DESCRIPTION
                      "Table of Call Home Exclusion Event entries information."
                     ::= { callHomeExclusionEvents 1 }

      readCallHomeExclusionEventEntry OBJECT-TYPE
                    SYNTAX   ReadCallHomeExclusionEventEntry
                    MAX-ACCESS  not-accessible
                    STATUS  current -- was mandatory
                    DESCRIPTION
                    "Call Home Exclusion Event table entry"
                    INDEX { readCallHomeExclusionEventIndex }
                    ::= { readCallHomeExclusionEventTable 1 }


      ReadCallHomeExclusionEventEntry::= SEQUENCE {
                 readCallHomeExclusionEventIndex INTEGER,
                 readCallHomeExclusionEventID OCTET STRING
                  }


     readCallHomeExclusionEventIndex  OBJECT-TYPE
                  SYNTAX  Integer32 (0..2147483647) -- was INTEGER
                  MAX-ACCESS  read-only
                  STATUS  current -- was mandatory
                  DESCRIPTION
                  "The index number of one Call Home Exclusion Event.  
                  For consistent results, view as a table and not as individual entries."
                  ::= { readCallHomeExclusionEventEntry 1 }

      readCallHomeExclusionEventID OBJECT-TYPE
                  SYNTAX  OCTET STRING
                  MAX-ACCESS  read-only
                  STATUS  current -- was mandatory
                  DESCRIPTION 
                  "The Event ID of one Call Home Exclusion Event entry.
                  For consistent results, view as a table and not as individual entries."
                  ::= { readCallHomeExclusionEventEntry 2 }   


      addCallHomeExclusionEvent  OBJECT-TYPE
                      SYNTAX  OCTET STRING 
                      MAX-ACCESS  read-write
                      STATUS  current -- was mandatory
                      DESCRIPTION
                      "Add one call home Event ID into the Call Home Exclusion List. 
                      The Event ID is an 8-digit hexadecimal number (0-F) with an optional prefix of '0x' or '0X'.
                      An Event can not be added into the exclusion list if autoFtpMode is disabled.
                      However, if Service Advisor Terms and Conditions are accepted, an event can be added into the exclusion list. 
                      
                      NOTE: Value returned for the GET command is meaningless for this MIB object."
                     ::= { callHomeExclusionEvents 2} 

    rmCallHomeExclusionEvent  OBJECT-TYPE
                      SYNTAX  OCTET STRING  
                      MAX-ACCESS  read-write
                      STATUS  current -- was mandatory
                      DESCRIPTION
                      "Remove one call home Event ID from the Call Home Exclusion List. 
                      The Event ID is an 8-digit hexadecimal number (0-F) with an optional prefix of '0x' or '0X'.
                      An event on the exclusion list can not be removed if autoFtpMode is disabled. 
                      However, if Service Advisor Terms and Conditions are accepted, an event on the exclusion list can be removed.
                      
                      NOTE: Value returned for the GET command is meaningless for this MIB object."
                     ::= { callHomeExclusionEvents 3}  
    rmAllCallHomeExclusionEvent  OBJECT-TYPE
                      SYNTAX  INTEGER {
                      execute(1)
                      }
                      MAX-ACCESS  read-write
                      STATUS  current -- was mandatory
                      DESCRIPTION
                      "Remove all Event IDs from the Call Home Exclusion List. 
                      Events on the exclusion list can not be removed if autoFtpMode is disabled.
                      However, if Service Advisor Terms and Conditions are accepted, events on the exclusion list can be removed.

                      NOTE: Value returned for the GET command is meaningless for this MIB object."
                     ::= { callHomeExclusionEvents 4} 
      

END
