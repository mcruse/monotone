-- **************************************************************************
-- **************************************************************************
--
-- File         : mmalert.mib
-- Description  : IBM Management Module traps
--                 MIB for traps(Alerts)
-- Version      : 4.5
-- Date         : October 2008
--
--
-- Copyright (c) 2002 - 2008 IBM  All Rights Reserved.
--
--
-- Contains trap descriptions for:
--  (1) Bladecenter Management Module
--
-- This MIB is used by the Management Module to describe
-- traps for alert conditions detected by the MM/Blades on Bladecenter hardware.
-- vvvvvvvvvvvvvvvvvvvvvvvvvvvvvvvvvvvvvvvvvvvvvvvvvvvvvvvvvvvvvvvvvvvvvvvvvv
-- MODIFICATIONS:
-- 20090731 markeva - Commented out mmTrapTempC TRAP because smidump said:
--             "last subidentifier assigned to `mmTrapTempC' may not be zero"
-- ^^^^^^^^^^^^^^^^^^^^^^^^^^^^^^^^^^^^^^^^^^^^^^^^^^^^^^^^^^^^^^^^^^^^^^^^^^
-- **************************************************************************
-- **************************************************************************

        BLADESPPALT-MIB DEFINITIONS ::= BEGIN


        IMPORTS
            OBJECT-TYPE                          FROM RFC-1212
            enterprises                          FROM RFC1155-SMI
            DisplayString                        FROM RFC1213-MIB
            TRAP-TYPE                            FROM RFC-1215;


        ibm            OBJECT IDENTIFIER ::=   { enterprises 2 }

        -- IBM products group

        ibmProd        OBJECT IDENTIFIER ::=   { ibm 6 }

        -- IBM Netfinity SP

        supportProcessor OBJECT IDENTIFIER ::= { ibmProd 158 }

        -- IBM Netfinity SP Alert

        mmRemoteSupTrapMIB     OBJECT IDENTIFIER ::= { supportProcessor 3 }

-- **************************************************************************
-- Start: Management Module Adapter SP Alerts
-- **************************************************************************

        -- the rsspalt generic trap generator group

        remoteSupTrapMibObjects OBJECT IDENTIFIER ::= { mmRemoteSupTrapMIB 1 }


        spTrapInfo OBJECT IDENTIFIER ::= { remoteSupTrapMibObjects 1 }

        spTrapDateTime  OBJECT-TYPE
                       SYNTAX  DisplayString
                       ACCESS  read-only
                       STATUS  mandatory
                       DESCRIPTION
                       "Timestamp of Local Date and Time when alert was generated"
                       ::= { spTrapInfo 1 }

        spTrapAppId    OBJECT-TYPE
                       SYNTAX  DisplayString
                       ACCESS  read-only
                       STATUS  mandatory
                       DESCRIPTION
                       "Application ID, always 'BladeCenter Management Module'"
                       ::= { spTrapInfo 2 }

        spTrapSpTxtId  OBJECT-TYPE
                       SYNTAX  DisplayString
                       ACCESS  read-only
                       STATUS  mandatory
                       DESCRIPTION
                       "SP System Identification - Text Identification"
                       ::= { spTrapInfo 3 }

        spTrapSysUuid  OBJECT-TYPE
                       SYNTAX  DisplayString
                       ACCESS  read-only
                       STATUS  mandatory
                       DESCRIPTION
                       "Host System UUID(Universal Unique ID)"
                       ::= { spTrapInfo 4 }

        spTrapSysSern  OBJECT-TYPE
                       SYNTAX  DisplayString
                       ACCESS  read-only
                       STATUS  mandatory
                       DESCRIPTION
                       "Host System Serial Number"
                       ::= { spTrapInfo 5 }

        spTrapAppType  OBJECT-TYPE
                       SYNTAX  INTEGER (1..65535)
                       ACCESS  read-only
                       STATUS  mandatory
                       DESCRIPTION
                       "Application Alert Type - Event Number ID"
                       ::= { spTrapInfo 6 }

        spTrapPriority  OBJECT-TYPE
                       SYNTAX  INTEGER (1..65535)
                       ACCESS  read-only
                       STATUS  mandatory
                       DESCRIPTION
                       "Alert Severity Value
                          - Critical Alert(0)
                          - Major(1)
                          - Non-Critical Alert(2)
                          - System Alert(4)
                          - Recovery Alert(8)
                          - Informational Only Alert(255)"
                       ::= { spTrapInfo 7 }

        spTrapMsgText  OBJECT-TYPE
                       SYNTAX  DisplayString
                       ACCESS  read-only
                       STATUS  mandatory
                       DESCRIPTION
                       "Alert Message Text"
                       ::= { spTrapInfo 8 }

        spTrapHostContact  OBJECT-TYPE
                       SYNTAX  DisplayString
                       ACCESS  read-only
                       STATUS  mandatory
                       DESCRIPTION
                       "Host Contact"
                       ::= { spTrapInfo 9 }

        spTrapHostLocation  OBJECT-TYPE
                       SYNTAX  DisplayString
                       ACCESS  read-only
                       STATUS  mandatory
                       DESCRIPTION
                       "Host Location"
                       ::= { spTrapInfo 10 }

        spTrapBladeName  OBJECT-TYPE
                       SYNTAX  DisplayString
                       ACCESS  read-only
                       STATUS  mandatory
                       DESCRIPTION
                       "Blade Name"
                       ::= { spTrapInfo 11 }

        spTrapBladeSern  OBJECT-TYPE
                       SYNTAX  DisplayString
                       ACCESS  read-only
                       STATUS  mandatory
                       DESCRIPTION
                       "Blade Serial Number"
                       ::= { spTrapInfo 12 }

        spTrapBladeUuid  OBJECT-TYPE
                       SYNTAX  DisplayString
                       ACCESS  read-only
                       STATUS  mandatory
                       DESCRIPTION
                       "Blade UUID(Universal Unique ID)"
                       ::= { spTrapInfo 13 }

        spTrapEvtName  OBJECT-TYPE
                       SYNTAX Unsigned32 (1..4294967295)
                       ACCESS  read-only
                       STATUS  mandatory
                       DESCRIPTION
                       "The 32 bit event name associated with the event that caused the trap"
                       ::= { spTrapInfo 14 }                       

        spTrapSourceId  OBJECT-TYPE
                       SYNTAX  DisplayString
                       ACCESS  read-only
                       STATUS  mandatory
                       DESCRIPTION
                       "The source identifier associated with the event that caused the trap"
                       ::= { spTrapInfo 15 }

        spTrapCallHomeFlag  OBJECT-TYPE
                       SYNTAX  Unsigned32 (1..4294967295)
                       ACCESS  read-only
                       STATUS  mandatory
                       DESCRIPTION
                       "The call home flag associated with the event that caused the trap"
                       ::= { spTrapInfo 16 }

        spTrapSysIPAddress  OBJECT-TYPE
                       SYNTAX  DisplayString
                       ACCESS  read-only
                       STATUS  mandatory
                       DESCRIPTION
                       "The AMM IP Address"
                       ::= { spTrapInfo 17 }

        spTrapSysMachineModel  OBJECT-TYPE
                       SYNTAX  DisplayString
                       ACCESS  read-only
                       STATUS  mandatory
                       DESCRIPTION
                       "Chassis Machine Type/Module"
                       ::= { spTrapInfo 18 }

        spTrapBladeMachineModel  OBJECT-TYPE
                       SYNTAX  DisplayString
                       ACCESS  read-only
                       STATUS  mandatory
                       DESCRIPTION
                       "Blade Machine Type/Module"
                       ::= { spTrapInfo 19 }

              
-- **************************************************************************
-- Critical Traps
-- **************************************************************************
        -- smidump says "last subidentifier assigned to `mmTrapTempC' may not be zero"
        -- mmTrapTempC          TRAP-TYPE
        --                         ENTERPRISE  mmRemoteSupTrapMIB
        --                         VARIABLES
        --                           {
        --                           spTrapDateTime,
        --                           spTrapAppId,
        --                           spTrapSpTxtId,
        --                           spTrapSysUuid,
        --                           spTrapSysSern,
        --                           spTrapAppType,
        --                           spTrapPriority,
        --                           spTrapMsgText,
        --                           spTrapHostContact,
        --                           spTrapHostLocation,
        --                           spTrapBladeName,
        --                           spTrapBladeSern,
        --                           spTrapBladeUuid,
        --                           spTrapEvtName,
        --                           spTrapSourceId,
        --                           spTrapCallHomeFlag,
        --                           spTrapSysIPAddress,
        --                           spTrapSysMachineModel,
        --                           spTrapBladeMachineModel
        --                           }
        --                           DESCRIPTION
        --                             "Critical Alert: Temperature threshold exceeded.
        --                             Note: This mib object will be replaced in a future release."
        --                           ::= 0

        mmTrapVoltC        TRAP-TYPE
                              ENTERPRISE  mmRemoteSupTrapMIB
                              VARIABLES
                                {
                                spTrapDateTime,
                                spTrapAppId,
                                spTrapSpTxtId,
                                spTrapSysUuid,
                                spTrapSysSern,
                                spTrapAppType,
                                spTrapPriority,
                                spTrapMsgText,
                                spTrapHostContact,
                                spTrapHostLocation,
                                spTrapBladeName,
                                spTrapBladeSern,
                                spTrapBladeUuid,
                                spTrapEvtName,
                                spTrapSourceId,
                                spTrapCallHomeFlag,
                                spTrapSysIPAddress,
                                spTrapSysMachineModel,  
                                spTrapBladeMachineModel 
                                }
                                DESCRIPTION
                                  "Critical Alert: Voltage threshold exceeded.
                                  Note: This mib object will be replaced in a future release."
                                ::= 1

        mmTrapTampC        TRAP-TYPE
                              ENTERPRISE  mmRemoteSupTrapMIB
                              VARIABLES
                                {
                                spTrapDateTime,
                                spTrapAppId,
                                spTrapSpTxtId,
                                spTrapSysUuid,
                                spTrapSysSern,
                                spTrapAppType,
                                spTrapPriority,
                                spTrapMsgText,
                                spTrapHostContact,
                                spTrapHostLocation,
                                spTrapBladeName,
                                spTrapBladeSern,
                                spTrapBladeUuid,
                                spTrapEvtName,
                                spTrapSourceId,
                                spTrapCallHomeFlag,
                                spTrapSysIPAddress,
                                spTrapSysMachineModel,  
                                spTrapBladeMachineModel 
                                }
                                DESCRIPTION
                                  "Critical Alert: Physical intrusion of system has occurred.
                                  Note: This mib object will be replaced in a future release."
                                ::= 2

        mmTrapMffC         TRAP-TYPE
                              ENTERPRISE  mmRemoteSupTrapMIB
                              VARIABLES
                                {
                                spTrapDateTime,
                                spTrapAppId,
                                spTrapSpTxtId,
                                spTrapSysUuid,
                                spTrapSysSern,
                                spTrapAppType,
                                spTrapPriority,
                                spTrapMsgText,
                                spTrapHostContact,
                                spTrapHostLocation,
                                spTrapBladeName,
                                spTrapBladeSern,
                                spTrapBladeUuid,
                                spTrapEvtName,
                                spTrapSourceId,
                                spTrapCallHomeFlag,
                                spTrapSysIPAddress,
                                spTrapSysMachineModel,  
                                spTrapBladeMachineModel 
                                }
                                DESCRIPTION
                                  "Critical Alert: Multiple fan failure.
                                  Note: This mib object will be replaced in a future release."
                                ::= 3

        mmTrapPsC          TRAP-TYPE
                              ENTERPRISE  mmRemoteSupTrapMIB
                              VARIABLES
                                {
                                spTrapDateTime,
                                spTrapAppId,
                                spTrapSpTxtId,
                                spTrapSysUuid,
                                spTrapSysSern,
                                spTrapAppType,
                                spTrapPriority,
                                spTrapMsgText,
                                spTrapHostContact,
                                spTrapHostLocation,
                                spTrapBladeName,
                                spTrapBladeSern,
                                spTrapBladeUuid,
                                spTrapEvtName,
                                spTrapSourceId,
                                spTrapCallHomeFlag,
                                spTrapSysIPAddress,
                                spTrapSysMachineModel,  
                                spTrapBladeMachineModel 
                                }
                                DESCRIPTION
                                  "Critical Alert: Power supply failure."
                                ::= 4

        mTrapHdC          TRAP-TYPE
                              ENTERPRISE  mmRemoteSupTrapMIB
                              VARIABLES
                                {
                                spTrapDateTime,
                                spTrapAppId,
                                spTrapSpTxtId,
                                spTrapSysUuid,
                                spTrapSysSern,
                                spTrapAppType,
                                spTrapPriority,
                                spTrapMsgText,
                                spTrapHostContact,
                                spTrapHostLocation,
                                spTrapBladeName,
                                spTrapBladeSern,
                                spTrapBladeUuid,
                                spTrapEvtName,
                                spTrapSourceId,
                                spTrapCallHomeFlag,
                                spTrapSysIPAddress,
                                spTrapSysMachineModel,  
                                spTrapBladeMachineModel 
                                }
                                DESCRIPTION
                                  "Critical Alert: Hard disk drive failure.
                                  Note: This mib object will be replaced in a future release."
                                ::= 5

        mmTrapVrmC         TRAP-TYPE
                              ENTERPRISE  mmRemoteSupTrapMIB
                              VARIABLES
                                {
                                spTrapDateTime,
                                spTrapAppId,
                                spTrapSpTxtId,
                                spTrapSysUuid,
                                spTrapSysSern,
                                spTrapAppType,
                                spTrapPriority,
                                spTrapMsgText,
                                spTrapHostContact,
                                spTrapHostLocation,
                                spTrapBladeName,
                                spTrapBladeSern,
                                spTrapBladeUuid,
                                spTrapEvtName,
                                spTrapSourceId,
                                spTrapCallHomeFlag,
                                spTrapSysIPAddress,
                                spTrapSysMachineModel,  
                                spTrapBladeMachineModel 
                                }
                                DESCRIPTION
                                  "Critical Alert: Voltage Regulator Module(VRM) failure.
                                  Note: This mib object will be replaced in a future release."
                                ::= 6

        mmTrapSffC         TRAP-TYPE
                              ENTERPRISE  mmRemoteSupTrapMIB
                              VARIABLES
                                {
                                spTrapDateTime,
                                spTrapAppId,
                                spTrapSpTxtId,
                                spTrapSysUuid,
                                spTrapSysSern,
                                spTrapAppType,
                                spTrapPriority,
                                spTrapMsgText,
                                spTrapHostContact,
                                spTrapHostLocation,
                                spTrapBladeName,
                                spTrapBladeSern,
                                spTrapBladeUuid,
                                spTrapEvtName,
                                spTrapSourceId,
                                spTrapCallHomeFlag,
                                spTrapSysIPAddress,
                                spTrapSysMachineModel ,  
                                spTrapBladeMachineModel 

                                }
                                DESCRIPTION
                                  "Critical Alert: Single Fan failure.
                                  Note: This mib object will be replaced in a future release."
                                ::= 11


        mmTrapMsC          TRAP-TYPE
                              ENTERPRISE  mmRemoteSupTrapMIB
                              VARIABLES
                                {
                                spTrapDateTime,
                                spTrapAppId,
                                spTrapSpTxtId,
                                spTrapSysUuid,
                                spTrapSysSern,
                                spTrapAppType,
                                spTrapPriority,
                                spTrapMsgText,
                                spTrapHostContact,
                                spTrapHostLocation,
                                spTrapBladeName,
                                spTrapBladeSern,
                                spTrapBladeUuid,
                                spTrapEvtName,
                                spTrapSourceId,
                                spTrapCallHomeFlag,
                                spTrapSysIPAddress,
                                spTrapSysMachineModel ,  
                                spTrapBladeMachineModel 
                                }
                                DESCRIPTION
                                  "Critical Alert: Multiple switch module failure.
                                  Note: This mib object will be replaced in a future release."
                                ::= 31

        mmTrapIhcC         TRAP-TYPE
                              ENTERPRISE  mmRemoteSupTrapMIB
                              VARIABLES
                                {
                                spTrapDateTime,
                                spTrapAppId,
                                spTrapSpTxtId,
                                spTrapSysUuid,
                                spTrapSysSern,
                                spTrapAppType,
                                spTrapPriority,
                                spTrapMsgText,
                                spTrapHostContact,
                                spTrapHostLocation,
                                spTrapBladeName,
                                spTrapBladeSern,
                                spTrapBladeUuid,
                                spTrapEvtName,
                                spTrapSourceId,
                                spTrapCallHomeFlag,
                                spTrapSysIPAddress,
                                spTrapSysMachineModel,  
                                spTrapBladeMachineModel 

                                }
                                DESCRIPTION
                                  "Critical Alert: Incompatible hardware configuration.
                                  Note: This mib object will be replaced in a future release."
                                ::= 36

        mmTrapBladeC          TRAP-TYPE 
                             ENTERPRISE  mmRemoteSupTrapMIB
                              VARIABLES
                                {
                                spTrapDateTime,
                                spTrapAppId,
                                spTrapSpTxtId,
                                spTrapSysUuid,
                                spTrapSysSern,
                                spTrapAppType,
                                spTrapPriority,
                                spTrapMsgText,
                                spTrapHostContact,
                                spTrapHostLocation,
                                spTrapBladeName,
                                spTrapBladeSern,
                                spTrapBladeUuid,
                                spTrapEvtName,
                                spTrapSourceId,
                                spTrapCallHomeFlag,
                                spTrapSysIPAddress,
                                spTrapSysMachineModel ,  
                                spTrapBladeMachineModel 
                                }
                                DESCRIPTION
                                  "Critical Alert: Blade."
                                ::= 128

        mmTrapIOC          TRAP-TYPE 
                             ENTERPRISE  mmRemoteSupTrapMIB
                              VARIABLES
                                {
                                spTrapDateTime,
                                spTrapAppId,
                                spTrapSpTxtId,
                                spTrapSysUuid,
                                spTrapSysSern,
                                spTrapAppType,
                                spTrapPriority,
                                spTrapMsgText,
                                spTrapHostContact,
                                spTrapHostLocation,
                                spTrapBladeName,
                                spTrapBladeSern,
                                spTrapBladeUuid,
                                spTrapEvtName,
                                spTrapSourceId,
                                spTrapCallHomeFlag,
                                spTrapSysIPAddress,
                                spTrapSysMachineModel ,  
                                spTrapBladeMachineModel 
                                }
                                DESCRIPTION
                                  "Critical Alert: I/O Module."
                                ::= 129

        mmTrapStorageC      TRAP-TYPE 
                             ENTERPRISE  mmRemoteSupTrapMIB
                              VARIABLES
                                {
                                spTrapDateTime,
                                spTrapAppId,
                                spTrapSpTxtId,
                                spTrapSysUuid,
                                spTrapSysSern,
                                spTrapAppType,
                                spTrapPriority,
                                spTrapMsgText,
                                spTrapHostContact,
                                spTrapHostLocation,
                                spTrapBladeName,
                                spTrapBladeSern,
                                spTrapBladeUuid,
                                spTrapEvtName,
                                spTrapSourceId,
                                spTrapCallHomeFlag,
                                spTrapSysIPAddress,
                                spTrapSysMachineModel,  
                                spTrapBladeMachineModel 
                                }
                                DESCRIPTION
                                  "Critical Alert: Storage Module."
                                ::= 131

        mmTrapChassisC      TRAP-TYPE 
                             ENTERPRISE  mmRemoteSupTrapMIB
                              VARIABLES
                                {
                                spTrapDateTime,
                                spTrapAppId,
                                spTrapSpTxtId,
                                spTrapSysUuid,
                                spTrapSysSern,
                                spTrapAppType,
                                spTrapPriority,
                                spTrapMsgText,
                                spTrapHostContact,
                                spTrapHostLocation,
                                spTrapBladeName,
                                spTrapBladeSern,
                                spTrapBladeUuid,
                                spTrapEvtName,
                                spTrapSourceId,
                                spTrapCallHomeFlag,
                                spTrapSysIPAddress,
                                spTrapSysMachineModel,  
                                spTrapBladeMachineModel 
                                }
                                DESCRIPTION
                                  "Critical Alert: Chassis Module."
                                ::= 130

        mmTrapFanC      TRAP-TYPE 
                             ENTERPRISE  mmRemoteSupTrapMIB
                              VARIABLES
                                {
                                spTrapDateTime,
                                spTrapAppId,
                                spTrapSpTxtId,
                                spTrapSysUuid,
                                spTrapSysSern,
                                spTrapAppType,
                                spTrapPriority,
                                spTrapMsgText,
                                spTrapHostContact,
                                spTrapHostLocation,
                                spTrapBladeName,
                                spTrapBladeSern,
                                spTrapBladeUuid,
                                spTrapEvtName,
                                spTrapSourceId,
                                spTrapCallHomeFlag,
                                spTrapSysIPAddress,
                                spTrapSysMachineModel,  
                                spTrapBladeMachineModel 
                                }
                                DESCRIPTION
                                  "Critical Alert: Cooling Devices."
                                ::= 133

-- **************************************************************************
-- Non-Critical Traps
-- **************************************************************************

        mmTrapRdpsN          TRAP-TYPE
                                ENTERPRISE  mmRemoteSupTrapMIB
                                VARIABLES
                                  {
                                  spTrapDateTime,
                                  spTrapAppId,
                                  spTrapSpTxtId,
                                  spTrapSysUuid,
                                  spTrapSysSern,
                                  spTrapAppType,
                                  spTrapPriority,
                                  spTrapMsgText,
                                  spTrapHostContact,
                                  spTrapHostLocation,
                                  spTrapBladeName,
                                  spTrapBladeSern,
                                  spTrapBladeUuid,
                                  spTrapEvtName,
                                  spTrapSourceId,
                                  spTrapCallHomeFlag,
                                  spTrapSysIPAddress,
                                  spTrapSysMachineModel,  
                                  spTrapBladeMachineModel 
                                  }
                                  DESCRIPTION
                                    "Non-Critical Alert: Redundant Power Supply failure.
                                  Note: This mib object will be replaced in a future release."
                                  ::= 10

        mmTrapTempN        TRAP-TYPE
                              ENTERPRISE  mmRemoteSupTrapMIB
                              VARIABLES
                                {
                                spTrapDateTime,
                                spTrapAppId,
                                spTrapSpTxtId,
                                spTrapSysUuid,
                                spTrapSysSern,
                                spTrapAppType,
                                spTrapPriority,
                                spTrapMsgText,
                                spTrapHostContact,
                                spTrapHostLocation,
                                spTrapBladeName,
                                spTrapBladeSern,
                                spTrapBladeUuid,
                                spTrapEvtName,
                                spTrapSourceId,
                                spTrapCallHomeFlag,
                                spTrapSysIPAddress,
                                spTrapSysMachineModel,  
                                spTrapBladeMachineModel 
                                }
                                DESCRIPTION
                                  "Non-Critical Alert: Temperature threshold exceeded.
                                  Note: This mib object will be replaced in a future release."
                                ::= 12

        mmTrapVoltN        TRAP-TYPE
                              ENTERPRISE  mmRemoteSupTrapMIB
                              VARIABLES
                                {
                                spTrapDateTime,
                                spTrapAppId,
                                spTrapSpTxtId,
                                spTrapSysUuid,
                                spTrapSysSern,
                                spTrapAppType,
                                spTrapPriority,
                                spTrapMsgText,
                                spTrapHostContact,
                                spTrapHostLocation,
                                spTrapBladeName,
                                spTrapBladeSern,
                                spTrapBladeUuid,
                                spTrapEvtName,
                                spTrapSourceId,
                                spTrapCallHomeFlag,
                                spTrapSysIPAddress,
                                spTrapSysMachineModel,  
                                spTrapBladeMachineModel 
                                }
                                DESCRIPTION
                                  "Non-Critical Alert: Voltage threshold exceeded.
                                  Note: This mib object will be replaced in a future release."
                                ::= 13

        mmTrapRmN          TRAP-TYPE
                              ENTERPRISE  mmRemoteSupTrapMIB
                              VARIABLES
                                {
                                spTrapDateTime,
                                spTrapAppId,
                                spTrapSpTxtId,
                                spTrapSysUuid,
                                spTrapSysSern,
                                spTrapAppType,
                                spTrapPriority,
                                spTrapMsgText,
                                spTrapHostContact,
                                spTrapHostLocation,
                                spTrapBladeName,
                                spTrapBladeSern,
                                spTrapBladeUuid,
                                spTrapEvtName,
                                spTrapSourceId,
                                spTrapCallHomeFlag,
                                spTrapSysIPAddress,
                                spTrapSysMachineModel,  
                                spTrapBladeMachineModel 

                                }
                                DESCRIPTION
                                  "Non-Critical Alert: Redundant module.
                                  Note: This mib object will be replaced in a future release."
                                ::= 32
                                
       mmTrapBladeN          TRAP-TYPE
                              ENTERPRISE  mmRemoteSupTrapMIB
                              VARIABLES
                                {
                                spTrapDateTime,
                                spTrapAppId,
                                spTrapSpTxtId,
                                spTrapSysUuid,
                                spTrapSysSern,
                                spTrapAppType,
                                spTrapPriority,
                                spTrapMsgText,
                                spTrapHostContact,
                                spTrapHostLocation,
                                spTrapBladeName,
                                spTrapBladeSern,
                                spTrapBladeUuid,
                                spTrapEvtName,
                                spTrapSourceId,
                                spTrapCallHomeFlag,
                                spTrapSysIPAddress,
                                spTrapSysMachineModel,  
                                spTrapBladeMachineModel 
                                }
                                DESCRIPTION
                                  "Non-Critical Alert: Blade "
                                ::= 160

       mmTrapION          TRAP-TYPE
                              ENTERPRISE  mmRemoteSupTrapMIB
                              VARIABLES
                                {
                                spTrapDateTime,
                                spTrapAppId,
                                spTrapSpTxtId,
                                spTrapSysUuid,
                                spTrapSysSern,
                                spTrapAppType,
                                spTrapPriority,
                                spTrapMsgText,
                                spTrapHostContact,
                                spTrapHostLocation,
                                spTrapBladeName,
                                spTrapBladeSern,
                                spTrapBladeUuid,
                                spTrapEvtName,
                                spTrapSourceId,
                                spTrapCallHomeFlag,
                                spTrapSysIPAddress,
                                spTrapSysMachineModel,  
                                spTrapBladeMachineModel 

                                }
                                DESCRIPTION
                                  "Non-Critical Alert: I/O Module"
                                ::= 161


        mmTrapLogFullN          TRAP-TYPE
                              ENTERPRISE  mmRemoteSupTrapMIB
                              VARIABLES
                                {
                                spTrapDateTime,
                                spTrapAppId,
                                spTrapSpTxtId,
                                spTrapSysUuid,
                                spTrapSysSern,
                                spTrapAppType,
                                spTrapPriority,
                                spTrapMsgText,
                                spTrapHostContact,
                                spTrapHostLocation,
                                spTrapBladeName,
                                spTrapBladeSern,
                                spTrapBladeUuid,
                                spTrapEvtName,
                                spTrapSourceId,
                                spTrapCallHomeFlag,
                                spTrapSysIPAddress,
                                spTrapSysMachineModel,  
                                spTrapBladeMachineModel 
                                }
                                DESCRIPTION
                                  "Non-Critical Alert: Event Log 100% Full."
                                ::= 7

        mmTrapStorageN       TRAP-TYPE
                              ENTERPRISE  mmRemoteSupTrapMIB
                              VARIABLES
                                {
                                spTrapDateTime,
                                spTrapAppId,
                                spTrapSpTxtId,
                                spTrapSysUuid,
                                spTrapSysSern,
                                spTrapAppType,
                                spTrapPriority,
                                spTrapMsgText,
                                spTrapHostContact,
                                spTrapHostLocation,
                                spTrapBladeName,
                                spTrapBladeSern,
                                spTrapBladeUuid,
                                spTrapEvtName,
                                spTrapSourceId,
                                spTrapCallHomeFlag,
                                spTrapSysIPAddress,
                                spTrapSysMachineModel,  
                                spTrapBladeMachineModel 
                                }
                                DESCRIPTION
                                  "Non-Critical Alert: Storage Module"
                                ::= 163

        mmTrapPowerN      TRAP-TYPE 
                             ENTERPRISE  mmRemoteSupTrapMIB
                              VARIABLES
                                {
                                spTrapDateTime,
                                spTrapAppId,
                                spTrapSpTxtId,
                                spTrapSysUuid,
                                spTrapSysSern,
                                spTrapAppType,
                                spTrapPriority,
                                spTrapMsgText,
                                spTrapHostContact,
                                spTrapHostLocation,
                                spTrapBladeName,
                                spTrapBladeSern,
                                spTrapBladeUuid,
                                spTrapEvtName,
                                spTrapSourceId,
                                spTrapCallHomeFlag,
                                spTrapSysIPAddress,
                                spTrapSysMachineModel,  
                                spTrapBladeMachineModel 
                                }
                                DESCRIPTION
                                  "Non-Critical Alert: Power Module."
                                ::= 164

        mmTrapChassisN      TRAP-TYPE 
                             ENTERPRISE  mmRemoteSupTrapMIB
                              VARIABLES
                                {
                                spTrapDateTime,
                                spTrapAppId,
                                spTrapSpTxtId,
                                spTrapSysUuid,
                                spTrapSysSern,
                                spTrapAppType,
                                spTrapPriority,
                                spTrapMsgText,
                                spTrapHostContact,
                                spTrapHostLocation,
                                spTrapBladeName,
                                spTrapBladeSern,
                                spTrapBladeUuid,
                                spTrapEvtName,
                                spTrapSourceId,
                                spTrapCallHomeFlag,
                                spTrapSysIPAddress,
                                spTrapSysMachineModel,  
                                spTrapBladeMachineModel 

                                }
                                DESCRIPTION
                                  "Non-Critical Alert: Chassis Module."
                                ::= 162

        mmTrapFanN      TRAP-TYPE 
                             ENTERPRISE  mmRemoteSupTrapMIB
                              VARIABLES
                                {
                                spTrapDateTime,
                                spTrapAppId,
                                spTrapSpTxtId,
                                spTrapSysUuid,
                                spTrapSysSern,
                                spTrapAppType,
                                spTrapPriority,
                                spTrapMsgText,
                                spTrapHostContact,
                                spTrapHostLocation,
                                spTrapBladeName,
                                spTrapBladeSern,
                                spTrapBladeUuid,
                                spTrapEvtName,
                                spTrapSourceId,
                                spTrapCallHomeFlag,
                                spTrapSysIPAddress,
                                spTrapSysMachineModel,  
                                spTrapBladeMachineModel 
                                }
                                DESCRIPTION
                                  "Non-Critical Alert: Cooling Devices."
                                ::= 165

-- **************************************************************************
-- System Traps
-- **************************************************************************

        mmTrapSecDvS       TRAP-TYPE
                              ENTERPRISE  mmRemoteSupTrapMIB
                              VARIABLES
                                {
                                spTrapDateTime,
                                spTrapAppId,
                                spTrapSpTxtId,
                                spTrapSysUuid,
                                spTrapSysSern,
                                spTrapAppType,
                                spTrapPriority,
                                spTrapMsgText,
                                spTrapHostContact,
                                spTrapHostLocation,
                                spTrapBladeName,
                                spTrapBladeSern,
                                spTrapBladeUuid,
                                spTrapEvtName,
                                spTrapSourceId,
                                spTrapCallHomeFlag,
                                spTrapSysIPAddress,
                                spTrapSysMachineModel,  
                                spTrapBladeMachineModel 
                                }
                                DESCRIPTION
                                  "System Alert: Secondary Device warning.
                                  Note: This mib object will be replaced in a future release."
                                ::= 15

        mmTrapPostToS      TRAP-TYPE
                              ENTERPRISE  mmRemoteSupTrapMIB
                              VARIABLES
                                {
                                spTrapDateTime,
                                spTrapAppId,
                                spTrapSpTxtId,
                                spTrapSysUuid,
                                spTrapSysSern,
                                spTrapAppType,
                                spTrapPriority,
                                spTrapMsgText,
                                spTrapHostContact,
                                spTrapHostLocation,
                                spTrapBladeName,
                                spTrapBladeSern,
                                spTrapBladeUuid,
                                spTrapEvtName,
                                spTrapSourceId,
                                spTrapCallHomeFlag,
                                spTrapSysIPAddress,
                                spTrapSysMachineModel,  
                                spTrapBladeMachineModel 
                                }
                                DESCRIPTION
                                  "System Alert: Post Timeout value exceeded.
                                  Note: This mib object will be replaced in a future release."
                                ::= 20

        mmTrapOsToS        TRAP-TYPE
                              ENTERPRISE  mmRemoteSupTrapMIB
                              VARIABLES
                                {
                                spTrapDateTime,
                                spTrapAppId,
                                spTrapSpTxtId,
                                spTrapSysUuid,
                                spTrapSysSern,
                                spTrapAppType,
                                spTrapPriority,
                                spTrapMsgText,
                                spTrapHostContact,
                                spTrapHostLocation,
                                spTrapBladeName,
                                spTrapBladeSern,
                                spTrapBladeUuid,
                                spTrapEvtName,
                                spTrapSourceId,
                                spTrapCallHomeFlag,
                                spTrapSysIPAddress,
                                spTrapSysMachineModel,  
                                spTrapBladeMachineModel 
                                }
                                DESCRIPTION
                                  "System Alert: OS Timeout value exceeded.
                                  Note: This mib object will be replaced in a future release."
                                ::= 21

        mmTrapAppS         TRAP-TYPE
                              ENTERPRISE  mmRemoteSupTrapMIB
                              VARIABLES
                                {
                                spTrapDateTime,
                                spTrapAppId,
                                spTrapSpTxtId,
                                spTrapSysUuid,
                                spTrapSysSern,
                                spTrapAppType,
                                spTrapPriority,
                                spTrapMsgText,
                                spTrapHostContact,
                                spTrapHostLocation,
                                spTrapBladeName,
                                spTrapBladeSern,
                                spTrapBladeUuid,
                                spTrapEvtName,
                                spTrapSourceId,
                                spTrapCallHomeFlag,
                                spTrapSysIPAddress,
                                spTrapSysMachineModel,  
                                spTrapBladeMachineModel 
                                }
                                DESCRIPTION
                                  "System Alert: Application Alert."
                                ::= 22
                                
        mmTrapPoffS        TRAP-TYPE
                              ENTERPRISE  mmRemoteSupTrapMIB
                              VARIABLES
                                {
                                spTrapDateTime,
                                spTrapAppId,
                                spTrapSpTxtId,
                                spTrapSysUuid,
                                spTrapSysSern,
                                spTrapAppType,
                                spTrapPriority,
                                spTrapMsgText,
                                spTrapHostContact,
                                spTrapHostLocation,
                                spTrapBladeName,
                                spTrapBladeSern,
                                spTrapBladeUuid,
                                spTrapEvtName,
                                spTrapSourceId,
                                spTrapCallHomeFlag,
                                spTrapSysIPAddress,
                                spTrapSysMachineModel,  
                                spTrapBladeMachineModel 

                                }
                                DESCRIPTION
                                  "System Alert: Power Off.
                                  Note: This mib object will be replaced in a future release."
                                ::= 23

        mmTrapPonS         TRAP-TYPE
                              ENTERPRISE  mmRemoteSupTrapMIB
                              VARIABLES
                                {
                                spTrapDateTime,
                                spTrapAppId,
                                spTrapSpTxtId,
                                spTrapSysUuid,
                                spTrapSysSern,
                                spTrapAppType,
                                spTrapPriority,
                                spTrapMsgText,
                                spTrapHostContact,
                                spTrapHostLocation,
                                spTrapBladeName,
                                spTrapBladeSern,
                                spTrapBladeUuid,
                                spTrapEvtName,
                                spTrapSourceId,
                                spTrapCallHomeFlag,
                                spTrapSysIPAddress,
                                spTrapSysMachineModel,  
                                spTrapBladeMachineModel 

                                }
                                DESCRIPTION
                                  "System Alert: Power On.
                                  Note: This mib object will be replaced in a future release."
                                ::= 24

        mmTrapBootS        TRAP-TYPE
                              ENTERPRISE  mmRemoteSupTrapMIB
                              VARIABLES
                                {
                                spTrapDateTime,
                                spTrapAppId,
                                spTrapSpTxtId,
                                spTrapSysUuid,
                                spTrapSysSern,
                                spTrapAppType,
                                spTrapPriority,
                                spTrapMsgText,
                                spTrapHostContact,
                                spTrapHostLocation,
                                spTrapBladeName,
                                spTrapBladeSern,
                                spTrapBladeUuid,
                                spTrapEvtName,
                                spTrapSourceId,
                                spTrapCallHomeFlag,
                                spTrapSysIPAddress,
                                spTrapSysMachineModel,  
                                spTrapBladeMachineModel 
                                }
                                DESCRIPTION
                                  "System Alert: System Boot Failure.
                                  Note: This mib object will be replaced in a future release."
                                ::= 25

        mmTrapLdrToS       TRAP-TYPE
                              ENTERPRISE  mmRemoteSupTrapMIB
                              VARIABLES
                                {
                                spTrapDateTime,
                                spTrapAppId,
                                spTrapSpTxtId,
                                spTrapSysUuid,
                                spTrapSysSern,
                                spTrapAppType,
                                spTrapPriority,
                                spTrapMsgText,
                                spTrapHostContact,
                                spTrapHostLocation,
                                spTrapBladeName,
                                spTrapBladeSern,
                                spTrapBladeUuid,
                                spTrapEvtName,
                                spTrapSourceId,
                                spTrapCallHomeFlag,
                                spTrapSysIPAddress,
                                spTrapSysMachineModel,  
                                spTrapBladeMachineModel 
                                }
                                DESCRIPTION
                                  "System Alert: OS Loader Timeout.
                                  Note: This mib object will be replaced in a future release."
                                ::= 26

        mmTrapPFAS         TRAP-TYPE
                              ENTERPRISE  mmRemoteSupTrapMIB
                              VARIABLES
                                {
                                spTrapDateTime,
                                spTrapAppId,
                                spTrapSpTxtId,
                                spTrapSysUuid,
                                spTrapSysSern,
                                spTrapAppType,
                                spTrapPriority,
                                spTrapMsgText,
                                spTrapHostContact,
                                spTrapHostLocation,
                                spTrapBladeName,
                                spTrapBladeSern,
                                spTrapBladeUuid,
                                spTrapEvtName,
                                spTrapSourceId,
                                spTrapCallHomeFlag,
                                spTrapSysIPAddress,
                                spTrapSysMachineModel,  
                                spTrapBladeMachineModel 
                                }
                                DESCRIPTION
                                  "System Alert: Predictive Failure Analysis(PFA) information.
                                  Note: This mib object will be replaced in a future release."
                                ::= 27

        mmTrapRemoteLoginS    TRAP-TYPE
                              ENTERPRISE  mmRemoteSupTrapMIB
                              VARIABLES
                                {
                                spTrapDateTime,
                                spTrapAppId,
                                spTrapSpTxtId,
                                spTrapSysUuid,
                                spTrapSysSern,
                                spTrapAppType,
                                spTrapPriority,
                                spTrapMsgText,
                                spTrapHostContact,
                                spTrapHostLocation,
                                spTrapBladeName,
                                spTrapBladeSern,
                                spTrapBladeUuid,
                                spTrapEvtName,
                                spTrapSourceId,
                                spTrapCallHomeFlag,
                                spTrapSysIPAddress,
                                spTrapSysMachineModel,  
                                spTrapBladeMachineModel 
                                }
                                DESCRIPTION
                                  "System Alert: Remote Login"
                                ::= 30


        mmTrapKVMSwitchS   TRAP-TYPE
                              ENTERPRISE  mmRemoteSupTrapMIB
                              VARIABLES
                                {
                                spTrapDateTime,
                                spTrapAppId,
                                spTrapSpTxtId,
                                spTrapSysUuid,
                                spTrapSysSern,
                                spTrapAppType,
                                spTrapPriority,
                                spTrapMsgText,
                                spTrapHostContact,
                                spTrapHostLocation,
                                spTrapBladeName,
                                spTrapBladeSern,
                                spTrapBladeUuid,
                                spTrapEvtName,
                                spTrapSourceId,
                                spTrapCallHomeFlag,
                                spTrapSysIPAddress,
                                spTrapSysMachineModel,  
                                spTrapBladeMachineModel 
                                }
                                DESCRIPTION
                                  "System Alert: Keyboard/Video/Mouse(KVM) or Medial Tray(MT) switching failure.  
                                  Note: This mib object will be replaced in a future release."
                                ::= 33

        mmTrapSysInvS      TRAP-TYPE
                              ENTERPRISE  mmRemoteSupTrapMIB
                              VARIABLES
                                {
                                spTrapDateTime,
                                spTrapAppId,
                                spTrapSpTxtId,
                                spTrapSysUuid,
                                spTrapSysSern,
                                spTrapAppType,
                                spTrapPriority,
                                spTrapMsgText,
                                spTrapHostContact,
                                spTrapHostLocation,
                                spTrapBladeName,
                                spTrapBladeSern,
                                spTrapBladeUuid,
                                spTrapEvtName,
                                spTrapSourceId,
                                spTrapCallHomeFlag,
                                spTrapSysIPAddress,
                                spTrapSysMachineModel,  
                                spTrapBladeMachineModel 
                                }
                                DESCRIPTION
                                  "System Alert: Inventory."
                                ::= 34

        mmTrapSysLogS      TRAP-TYPE
                              ENTERPRISE  mmRemoteSupTrapMIB
                              VARIABLES
                                {
                                spTrapDateTime,
                                spTrapAppId,
                                spTrapSpTxtId,
                                spTrapSysUuid,
                                spTrapSysSern,
                                spTrapAppType,
                                spTrapPriority,
                                spTrapMsgText,
                                spTrapHostContact,
                                spTrapHostLocation,
                                spTrapBladeName,
                                spTrapBladeSern,
                                spTrapBladeUuid,
                                spTrapEvtName,
                                spTrapSourceId,
                                spTrapCallHomeFlag,
                                spTrapSysIPAddress,
                                spTrapSysMachineModel,  
                                spTrapBladeMachineModel 
                                }
                                DESCRIPTION
                                  "System Alert: System Log 75% full."
                                ::= 35

        mmTrapNwChangeS    TRAP-TYPE
                              ENTERPRISE  mmRemoteSupTrapMIB
                              VARIABLES
                                {
                                spTrapDateTime,
                                spTrapAppId,
                                spTrapSpTxtId,
                                spTrapSysUuid,
                                spTrapSysSern,
                                spTrapAppType,
                                spTrapPriority,
                                spTrapMsgText,
                                spTrapHostContact,
                                spTrapHostLocation,
                                spTrapBladeName,
                                spTrapBladeSern,
                                spTrapBladeUuid,
                                spTrapEvtName,
                                spTrapSourceId,
                                spTrapCallHomeFlag,
                                spTrapSysIPAddress,
                                spTrapSysMachineModel,  
                                spTrapBladeMachineModel 
                                }
                                DESCRIPTION
                                  "System Alert: Network change notification."
                                ::= 37

        mmTrapBlThrS          TRAP-TYPE
                              ENTERPRISE  mmRemoteSupTrapMIB
                              VARIABLES
                                {
                                spTrapDateTime,
                                spTrapAppId,
                                spTrapSpTxtId,
                                spTrapSysUuid,
                                spTrapSysSern,
                                spTrapAppType,
                                spTrapPriority,
                                spTrapMsgText,
                                spTrapHostContact,
                                spTrapHostLocation,
                                spTrapBladeName,
                                spTrapBladeSern,
                                spTrapBladeUuid,
                                spTrapEvtName,
                                spTrapSourceId,
                                spTrapCallHomeFlag,
                                spTrapSysIPAddress,
                                spTrapSysMachineModel,  
                                spTrapBladeMachineModel 
                                }
                                DESCRIPTION
                                  "System Alert: Blade Throttle.
                                  Note: This mib object will be replaced in a future release."
                                ::= 39

        mmTrapPwrMgntS          TRAP-TYPE
                              ENTERPRISE  mmRemoteSupTrapMIB
                              VARIABLES
                                {
                                spTrapDateTime,
                                spTrapAppId,
                                spTrapSpTxtId,
                                spTrapSysUuid,
                                spTrapSysSern,
                                spTrapAppType,
                                spTrapPriority,
                                spTrapMsgText,
                                spTrapHostContact,
                                spTrapHostLocation,
                                spTrapBladeName,
                                spTrapBladeSern,
                                spTrapBladeUuid,
                                spTrapEvtName,
                                spTrapSourceId,
                                spTrapCallHomeFlag,
                                spTrapSysIPAddress,
                                spTrapSysMachineModel,  
                                spTrapBladeMachineModel 
                                }
                                DESCRIPTION
                                  "System Alert: Power Management.
                                  Note: This mib object will be replaced in a future release."
                                ::= 40

        mmTrapBladeS        TRAP-TYPE
                              ENTERPRISE  mmRemoteSupTrapMIB
                              VARIABLES
                                {
                                spTrapDateTime,
                                spTrapAppId,
                                spTrapSpTxtId,
                                spTrapSysUuid,
                                spTrapSysSern,
                                spTrapAppType,
                                spTrapPriority,
                                spTrapMsgText,
                                spTrapHostContact,
                                spTrapHostLocation,
                                spTrapBladeName,
                                spTrapBladeSern,
                                spTrapBladeUuid,
                                spTrapEvtName,
                                spTrapSourceId,
                                spTrapCallHomeFlag,
                                spTrapSysIPAddress,
                                spTrapSysMachineModel,  
                                spTrapBladeMachineModel 
                                }
                                DESCRIPTION
                                  "System Alert: Blade"
                                ::= 176

        mmTrapIOS        TRAP-TYPE
                              ENTERPRISE  mmRemoteSupTrapMIB
                              VARIABLES
                                {
                                spTrapDateTime,
                                spTrapAppId,
                                spTrapSpTxtId,
                                spTrapSysUuid,
                                spTrapSysSern,
                                spTrapAppType,
                                spTrapPriority,
                                spTrapMsgText,
                                spTrapHostContact,
                                spTrapHostLocation,
                                spTrapBladeName,
                                spTrapBladeSern,
                                spTrapBladeUuid,
                                spTrapEvtName,
                                spTrapSourceId,
                                spTrapCallHomeFlag,
                                spTrapSysIPAddress,
                                spTrapSysMachineModel,  
                                spTrapBladeMachineModel 
                                }
                                DESCRIPTION
                                  "System Alert: I/O Module"
                                ::= 177

        mmTrapStorageS      TRAP-TYPE
                              ENTERPRISE  mmRemoteSupTrapMIB
                              VARIABLES
                                {
                                spTrapDateTime,
                                spTrapAppId,
                                spTrapSpTxtId,
                                spTrapSysUuid,
                                spTrapSysSern,
                                spTrapAppType,
                                spTrapPriority,
                                spTrapMsgText,
                                spTrapHostContact,
                                spTrapHostLocation,
                                spTrapBladeName,
                                spTrapBladeSern,
                                spTrapBladeUuid,
                                spTrapEvtName,
                                spTrapSourceId,
                                spTrapCallHomeFlag,
                                spTrapSysIPAddress,
                                spTrapSysMachineModel,  
                                spTrapBladeMachineModel 
                                }
                                DESCRIPTION
                                  "System Alert: Storage Module"
                                ::= 179

        mmTrapPowerS      TRAP-TYPE 
                             ENTERPRISE  mmRemoteSupTrapMIB
                              VARIABLES
                                {
                                spTrapDateTime,
                                spTrapAppId,
                                spTrapSpTxtId,
                                spTrapSysUuid,
                                spTrapSysSern,
                                spTrapAppType,
                                spTrapPriority,
                                spTrapMsgText,
                                spTrapHostContact,
                                spTrapHostLocation,
                                spTrapBladeName,
                                spTrapBladeSern,
                                spTrapBladeUuid,
                                spTrapEvtName,
                                spTrapSourceId,
                                spTrapCallHomeFlag,
                                spTrapSysIPAddress,
                                spTrapSysMachineModel,  
                                spTrapBladeMachineModel 
                                }
                                DESCRIPTION
                                  "System Alert: Power Module."
                                ::= 180

        mmTrapChassisS      TRAP-TYPE 
                             ENTERPRISE  mmRemoteSupTrapMIB
                              VARIABLES
                                {
                                spTrapDateTime,
                                spTrapAppId,
                                spTrapSpTxtId,
                                spTrapSysUuid,
                                spTrapSysSern,
                                spTrapAppType,
                                spTrapPriority,
                                spTrapMsgText,
                                spTrapHostContact,
                                spTrapHostLocation,
                                spTrapBladeName,
                                spTrapBladeSern,
                                spTrapBladeUuid,
                                spTrapEvtName,
                                spTrapSourceId,
                                spTrapCallHomeFlag,
                                spTrapSysIPAddress,
                                spTrapSysMachineModel,  
                                spTrapBladeMachineModel 
                                }
                                DESCRIPTION
                                  "System Alert: Chassis Module."
                                ::= 178

        mmTrapFanS      TRAP-TYPE 
                             ENTERPRISE  mmRemoteSupTrapMIB
                              VARIABLES
                                {
                                spTrapDateTime,
                                spTrapAppId,
                                spTrapSpTxtId,
                                spTrapSysUuid,
                                spTrapSysSern,
                                spTrapAppType,
                                spTrapPriority,
                                spTrapMsgText,
                                spTrapHostContact,
                                spTrapHostLocation,
                                spTrapBladeName,
                                spTrapBladeSern,
                                spTrapBladeUuid,
                                spTrapEvtName,
                                spTrapSourceId,
                                spTrapCallHomeFlag,
                                spTrapSysIPAddress,
                                spTrapSysMachineModel,  
                                spTrapBladeMachineModel 
                                }
                                DESCRIPTION
                                  "System Alert: Cooling Devices."
                                ::= 181

        mmTrapPwrDOS      TRAP-TYPE 
                             ENTERPRISE  mmRemoteSupTrapMIB
                              VARIABLES
                                {
                                spTrapDateTime,
                                spTrapAppId,
                                spTrapSpTxtId,
                                spTrapSysUuid,
                                spTrapSysSern,
                                spTrapAppType,
                                spTrapPriority,
                                spTrapMsgText,
                                spTrapHostContact,
                                spTrapHostLocation,
                                spTrapBladeName,
                                spTrapBladeSern,
                                spTrapBladeUuid,
                                spTrapEvtName,
                                spTrapSourceId,
                                spTrapCallHomeFlag,
                                spTrapSysIPAddress,
                                spTrapSysMachineModel,  
                                spTrapBladeMachineModel 
                                }
                                DESCRIPTION
                                  "System Alert: Power down or on."
                                ::= 182

END
